/*
 * Copyright (c) 2016 Cisco Systems, Inc. All rights reserved.
 *
 * This program and the accompanying materials are made available under the
 * terms of the Eclipse Public License v1.0 which accompanies this distribution,
 * and is available at http://www.eclipse.org/legal/epl-v10.html INTERNAL
 */
module onf-core-network-types {
  namespace "urn:onf:core-network-types";
  prefix onf-cnt;

  revision 2016-06-30 {
  }

  typedef OperType {
    type enumeration {
      enum REVERTIVE;
      enum NON-REVERTIVE;
    }
  }

  typedef LayerProtocolName {
    type string;
  }

  typedef ForwardingDirection {
    type enumeration {
      enum BIDIRECTIONAL;
      enum UNIDIRECTIONAL;
      enum UNDEFINED_OR_UNKNOWN;
    }
  }

  typedef PortRole {
    status current;
    type string;
  }

  typedef PortDirection {
    type enumeration {
      enum BIDIRECTIONAL;
      enum INPUT;
      enum OUTPUT;
      enum UNIDENTIFIED_OR_UNKNOWN;
    }
  }

  typedef ProtectionType {
    status deprecated;
    type string;
  }

  typedef TerminationDirection {
    type enumeration {
      enum BIDIRECTIONAL;
      enum SINK;
      enum SOURCE;
      enum UNDEFINED_OR_UNKNOWN;
    }
  }

}
