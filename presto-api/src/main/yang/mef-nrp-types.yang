/*
 * Copyright (c) 2016 Cisco Systems, Inc. All rights reserved.
 *
 * This program and the accompanying materials are made available under the
 * terms of the Eclipse Public License v1.0 which accompanies this distribution,
 * and is available at http://www.eclipse.org/legal/epl-v10.html INTERNAL
 */
module mef-nrp-types {
  namespace "urn:mef:nrp-types";
  prefix nrp-types;

  revision 2016-06-30 {
  }

  grouping G_NRP_SourceMacAddressLimit {
    leaf enabled {
      type boolean;
    }
    leaf limit {
      type NRP_NaturalNumber;
    }
    leaf timeInterval {
      type NRP_NaturalNumber;
    }
  }
  grouping G_NRP_VlanId {
    leaf vid {
      type NRP_PositiveInteger;
    }
  }
  typedef NRP_EvcEndPointRole {
    type enumeration {
      enum ROOT;
      enum LEAF;
    }
  }
  typedef NRP_Identifier45 {
    type string;
  }
  typedef NRP_L2cpAddressSet {
    type enumeration {
      enum CTA;
      enum CTB;
      enum CTB2;
    }
  }
  typedef NRP_PhysicalLayer {
    type enumeration {
      enum 10BASE2;
      enum 10BASE5;
      enum 10BASE_F;
      enum 10BASE_FB;
      enum 10BASE_FL;
      enum 10BASE_FP;
      enum 10BASE_T;
      enum 10BASE_TE;
      enum 10BROAD36;
      enum 10PASS_TS;
      enum 100BASE_BX10;
      enum 100BASE_FX;
      enum 100BASE_LX10;
      enum 100BASE_T;
      enum 100BASE_T2;
      enum 100BASE_T4;
      enum 100BASE_TX;
      enum 100BASE_X;
      enum 1000BASE_BX10;
      enum 1000BASE_CX;
      enum 1000BASE_KX;
      enum 1000BASE_LX;
      enum 1000BASE_LX10;
      enum 1000BASE_PX10;
      enum 1000BASE_PX20;
      enum 1000BASE_SX;
      enum 1000BASE_T;
      enum 1000BASE_X;
      enum 10GBASE_CX4;
      enum 10GBASE_E;
      enum 10GBASE_ER;
      enum 10GBASE_EW;
      enum 10GBASE_KR;
      enum 10GBASE_KX4;
      enum 10GBASE_L;
      enum 10GBASE_LR;
      enum 10GBASE_LRM;
      enum 10GBASE_LW;
      enum 10GBASE_LX4;
      enum 10GBASE_PR;
      enum 10GBASE_PRX;
      enum 10GBASE_R;
      enum 10GBASE_S;
      enum 10GBASE_SR;
      enum 10GBASE_SW;
      enum 10GBASE_T;
      enum 10GBASE_W;
      enum 10GBASE_X;
      enum 100GBASE_R;
      enum 100GBASE_CR10;
      enum 100GBASE_ER4;
      enum 100GBASE_LR4;
      enum 100GBASE_SR10;
      enum 40GBASE_R;
      enum 40GBASE_CR4;
      enum 40GBASE__FR;
      enum 40GBASE_KR4;
      enum 40GBASE_LR4;
      enum 40GBASE_SR4;
      enum 1BASE5;
      enum 2BASE_TL;
      enum 1G_EPON;
      enum 10G_EPON;
      enum 10_1G_EPON;
      enum 10_10G_EPON;
      enum NONE;
    }
  }
  typedef NRP_NaturalNumber {
    type uint32 {
      range "1..max";
    }
  }
  grouping G_NRP_SyncModePerLink {
    leaf linkId {
      type string;
    }
    leaf syncModeEnabled {
      type boolean;
    }
  }
  typedef NRP_ProtocolFrameType {
    type enumeration {
      enum ETHERTYPE;
      enum LLC_ADDRESS;
      enum OTHER;
    }
  }
  typedef NRP_InterfaceResiliency {
    type enumeration {
      enum NONE;
      enum 2_LINK_ACTIVE_STANDBY;
      enum ALL_ACTIVE;
      enum OTHER;
    }
  }
  grouping G_NRP_ConversationIdToAggrgationLinkMap {
    leaf conversationId {
      type NRP_NaturalNumber;
    }
    leaf linkId {
      type NRP_NaturalNumber;
    }
  }
  grouping G_NRP_L2cpPeering {
    leaf destinationMacAddress {
      type string;
      description "The destination address determines the intended recipient device for the frame.";
    }
    leaf protocolType {
      type NRP_ProtocolFrameType;
      description "Protocol Identifier is either an LLC Address or an Ethertype, and it could have subtypes. The list specifies only the L2CP Frames that
are to be Peered. Any L2CP Frame that is not Peered will either be Discarded or Passed
as a result of the flow charts and requirements specified in MEF 45, Section 9.";
    }
    leaf linkId {
      type string;
      description "Identifies the physical link identifier for protocols (e.g. LLDP, ESMC) that can operate over the individual physical links.
If no link identifier is specified then the list entry will apply to all physical links. 
MEF 45, Section 8.2";
    }
    leaf protocolId {
      type string;
    }
  }
  typedef NRP_ColorMode {
    type enumeration {
      enum COLOR_AWARE;
      enum COLOR_BLIND;
    }
  }
  typedef NRP_PositiveInteger {
    type uint32 {
      range "1..max";
    }
  }
  typedef NRP_VlanTag {
    type enumeration {
      enum S_TAG;
      enum C_TAG;
    }
  }
  typedef NRP_IpVersion {
    type enumeration {
      enum IPV4;
      enum IPV6;
      enum IPV4_AND_IPV6;
    }
  }
  typedef NRP_FrameColor {
    type enumeration {
      enum GREEN;
      enum YELLOW;
    }
  }
  typedef NRP_PcpOrDiscard {
    type enumeration {
      enum DISCARD;
      enum 0;
      enum 1;
      enum 2;
      enum 3;
      enum 4;
      enum 5;
      enum 6;
      enum 7;
    }
  }
  typedef NRP_DeiOrDiscard {
    type enumeration {
      enum DISCARD;
      enum 0;
      enum 1;
    }
  }
  grouping G_NRP_AggLinkDepth {
    container nrp_vlanId {
      config true;
      uses G_NRP_VlanId;
    }
    leaf nrp_linkNumber {
      type NRP_NaturalNumber;
    }
  }
  typedef NRP_ConnectionType {
    type enumeration {
      enum POINT_TO_POINT;
      enum MULTIPOINT;
      enum ROOTED_MULTIPOINT;
    }
  }
  typedef NRP_ServiceFrameDelivery {
    type enumeration {
      enum CONDITIONALLY;
      enum UNCONDITIONALLY;
    }
  }
  typedef NRP_EndPointRole {
    type enumeration {
      enum ROOT;
      enum LEAF;
      enum TRUNK;
    }
  }
  typedef NRP_MepDirection {
    type enumeration {
      enum DOWN;
      enum UP;
    }
  }
  grouping G_NRP_MepLevelAndDirection {
    leaf nrp_level {
      type NRP_NaturalNumber;
    }
    leaf nrp_direction {
      type NRP_MepDirection;
    }
    leaf nrp_megId {
      type string;
    }
  }
}
