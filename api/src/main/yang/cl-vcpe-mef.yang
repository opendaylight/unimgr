/*
 * Copyright (c) 2015 Cable Television Laboratories, Inc. All rights reserved.
 *
 * This program and the accompanying materials are made available under the
 * terms of the Eclipse Public License v1.0 which accompanies this distribution,
 * and is available at http://www.eclipse.org/legal/epl-v10.html INTERNAL
 */

// Constructed based on Adolfo's UML UNI model
// UNI
// + uniIdentifier : string
// + physicalMedium : string = UNI Type 2 Physical Interface
// + speed : string = Set (10M, 100M, 10M/100M, 10M/100M/1000M, 1G, 10G>
// + mode : string = Full Duplex
// + macLayer : string = IEEE 802.3-2005
// + type : string
// + uniMtuSize : int = [uniMtuSize >= 1522]

module cl-vcpe-mef {

    yang-version 1;
    namespace "urn:opendaylight:params:xml:ns:yang:vcpe";
    prefix "vcpe";

    import ietf-yang-types { prefix yang; revision-date 2013-07-15; }
    import ietf-inet-types { prefix inet; revision-date 2010-09-24; }
    import network-topology { prefix topo; revision-date 2013-10-21; }
    import yang-ext { prefix ext; }

    revision "2015-06-22" {
        description "Initial revision of vcpe model";
    }

    grouping service-speed {
        choice speed {
            case speed-10M {
                leaf speed-10M {
                    type empty;
                }
            }
            case speed-100M {
                leaf speed-100M {
                    type empty;
                }
            }
            case speed-1G {
                leaf speed-1G {
                    type empty;
                }
            }
            case speed-10G {
                leaf speed-10G {
                    type empty;
                }
            }
        }
    }

    // represent simplification of MEF Per Uni Attributes
    grouping uni {
        leaf id {
            type topo:node-id;
            //mandatory true;
            description "Uniquely identifies the uni";
        }
        leaf ovsdb-node-id {
            type topo:node-id;
            //mandatory false;
            description "Uniquely identifies the uni and ovsdb";
        }
        leaf physical-medium {
            type string;
            default "UNI TypeFull Duplex 2 Physical Interface";
        }
        leaf ip-address {
            type inet:ip-address;
        }
        leaf mac-address {
           type yang:mac-address;
        }
        container speed {
            uses service-speed;
        }
        leaf mode {
            type string;
            default "Full Duplex";
        }
        leaf mac-layer {
            type string;
            default "IEEE 802.3-2005";
        }
        leaf type {
            type string;
        }
        leaf mtu-size {
            type uint64;
            units byte;
        }
    }

    // Represents simplification of MEF EVC Per Uni Atrributes
    grouping evc {
        leaf id {
            type topo:node-id;
            //mandatory true;
            description "Uniquely identifies the evc";
        }
        list uni-source {
            key "order";
            leaf order {
                type uint8;
            }
            leaf uni {
                type topo:node-id;
            }
        }
        list uni-dest {
            key "order";
            leaf order {
                type uint8;
            }
            leaf uni {
                type topo:node-id;
            }
        }
        leaf cos-id {
            type string;
        }
        container ingress-bw {
            uses service-speed;
        }
        container egress-bw {
            uses service-speed;
        }
    }
    augment "/topo:network-topology/topo:topology/topo:node" {
        description "Augmentation for UNI nodes under topology";
        ext:augment-identifier "uni-augmentation";
        uses uni;
    }
    augment "/topo:network-topology/topo:topology/topo:link" {
        description "Augmentation for EVC Link under topology";
        ext:augment-identifier "evc-augmentation";
        uses evc;
    }

    container unis {
        list uni {
            key "id";
            uses uni;
        }
    }

    container evcs {
        list evc {
            key "id";
            uses evc;
        }
    }
}
