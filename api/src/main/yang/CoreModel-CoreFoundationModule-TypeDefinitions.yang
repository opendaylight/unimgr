module CoreModel-CoreFoundationModule-TypeDefinitions {
    namespace "uri:onf:CoreModel-CoreFoundationModule-TypeDefinitions";
    prefix CoreModel-CoreFoundationModule-TypeDefinitions;
    revision 2016-04-13{}
    typedef DateAndTime {
        type string;
    }
    typedef BitString {
        type string;
    }
    typedef Real {
        type string;
    }
    typedef PrintableString {
        type string;
    }
}
