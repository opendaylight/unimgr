module CoreModel-CoreNetworkModule-ObjectClasses {
    namespace "uri:onf:CoreModel-CoreNetworkModule-ObjectClasses";
    prefix CoreModel-CoreNetworkModule-ObjectClasses;
    import CoreModel-CoreFoundationModule-SuperClassesAndCommonPackages {
        prefix CoreModel-CoreFoundationModule-SuperClassesAndCommonPackages;
    }
    import CoreModel-CoreNetworkModule-TypeDefinitions {
        prefix CoreModel-CoreNetworkModule-TypeDefinitions;
    }
    import CoreModel-CoreModelEnhancements-ProfilesTemplatesAndSpecificationsModule {
        prefix CoreModel-CoreModelEnhancements-ProfilesTemplatesAndSpecificationsModule;
    }
    import CoreModel-CoreModelEnhancements-FcSwitchEnhancements_Developed {
        prefix CoreModel-CoreModelEnhancements-FcSwitchEnhancements_Developed;
    }
    revision 2016-04-13{}
    list ForwardingDomain {
        key 'uuid';
        config true;
        ordered-by system;
        uses G_ForwardingDomain;
    }
    grouping G_ForwardingDomain {
        uses CoreModel-CoreFoundationModule-SuperClassesAndCommonPackages:G_GlobalClass;
        uses G_TopologicalEntity;
        leaf-list layerProtocolNameList {
            description "One or more protocol layers at which the FD represents the opportunity to enable forwarding between LTP that bound it.";
            ordered-by system;
            type CoreModel-CoreNetworkModule-TypeDefinitions:LayerProtocolName;
            min-elements 1;
        }
        leaf-list _lowerLevelFdRefList {
            description "The FD object class supports a recursive aggregation relationship (HigherLevelFdEncompassesLowerLevelFds) such that the internal construction of an FD can be exposed as multiple lower level FDs and associated Links (partitioning).
The aggregated FDs and Links form an interconnected topology that provides and describes the capability of the aggregating FD.
Note that the model actually represents aggregation of lower level FDs into higher level FDs as views rather than FD partition, and supports multiple views. 
Aggregation allow reallocation of capacity from lower level FDs to different higher level FDs as if the network is reorganized  (as the association is aggregation not composition).";
            ordered-by system;
            type leafref {
                path '/ForwardingDomain/uuid';
            }
        }
        leaf-list _fcRefList {
            description "An FD contains one or more FCs. A contained FC connects LTPs that bound the FD.";
            ordered-by system;
            type leafref {
                path '/CoreModel-CoreNetworkModule-ObjectClasses:ForwardingConstructList/CoreModel-CoreNetworkModule-ObjectClasses:ForwardingConstruct/CoreModel-CoreNetworkModule-ObjectClasses:uuid';
            }
        }
        leaf-list _ltpRefList {
            description "An instance of FD is associated with zero or more LTP objects. 
The LTPs that bound the FD provide capacity for forwarding.";
            ordered-by system;
            type leafref {
                path '/CoreModel-CoreNetworkModule-ObjectClasses:LogicalTerminationPoint/CoreModel-CoreNetworkModule-ObjectClasses:uuid';
            }
        }
        leaf-list _linkRefList {
            description "The FD encompasses Links that interconnect lower level FDs and collect links that are wholly within the bounds of the FD.
See also _lowerLevelFdRefList.";
            ordered-by system;
            type leafref {
                path '/CoreModel-CoreNetworkModule-ObjectClasses:Link/CoreModel-CoreNetworkModule-ObjectClasses:uuid';
            }
        }
    }
    container ForwardingConstructList {
      list ForwardingConstruct {
        key 'uuid';
        config true;
        ordered-by system;
        uses G_ForwardingConstruct;
      }
    }
    grouping G_ForwardingConstruct {
        leaf uuid {
            type string;
        }
        leaf layerProtocolName {
            type CoreModel-CoreNetworkModule-TypeDefinitions:LayerProtocolName;
            description "The layerProtocol at which the FC enables potential for forwarding.";
        }
        leaf-list _lowerLevelFcRefList {
            description "An FC object supports a recursive aggregation relationship such that the internal construction of an FC can be exposed as multiple lower level FC objects (partitioning).
Aggregation is used as for the FD to allow changes in hierarchy.
";
            ordered-by system;
            type leafref {
                path '/CoreModel-CoreNetworkModule-ObjectClasses:ForwardingConstructList/CoreModel-CoreNetworkModule-ObjectClasses:ForwardingConstruct/CoreModel-CoreNetworkModule-ObjectClasses:uuid';
            }
        }
        leaf-list _fcRouteRefList {
            description "An FC object can have zero or more routes, each of which is defined as a list of lower level FC objects describing the flow across the network.";
            ordered-by system;
            type leafref {
                path '/CoreModel-CoreNetworkModule-ObjectClasses:FcRouteList/CoreModel-CoreNetworkModule-ObjectClasses:FcRoute/CoreModel-CoreNetworkModule-ObjectClasses:id';
            }
        }
        list FcPort {
            description "The association of the FC to LTPs is made via FcPorts (essentially the ports of the FC).";
            key 'id';
            config true;
            ordered-by system;
            uses G_FcPort;
            min-elements 2;
        }
        list _fcSwitchList {
            description "If an FC exposes protection (having two FcPorts that provide alternative identical inputs/outputs), the FC will have one or more associated FcSwitch objects.
The arrangement of switches for a particular instance is described by a referenced FcSpec";
            key 'id';
            config true;
            ordered-by system;
            uses G_FcSwitch;
        }
        list _configurationAndSwitchControlList {
            description "A multi-switch controller encapsulated in the FC.
The multi-switch controller coordinates multiple switches in the same FC.";
            key 'id';
            config true;
            ordered-by system;
            uses G_ConfigurationAndSwitchController;
        }
        leaf _fcSpecRef {
            type leafref {
                path '/CoreModel-CoreModelEnhancements-ProfilesTemplatesAndSpecificationsModule:FcSpecList/CoreModel-CoreModelEnhancements-ProfilesTemplatesAndSpecificationsModule:FcSpec/CoreModel-CoreModelEnhancements-ProfilesTemplatesAndSpecificationsModule:uuid';
            }
            description "References the specification that describes the capability and internal structure of of the FC (e.g. The arrangement of switches for a particular instance is described by a referenced FcSpec).
The specification allows interpretation of FcPort role and switch configurations etc.";
        }
        leaf forwardingDirection {
            type CoreModel-CoreNetworkModule-TypeDefinitions:ForwardingDirection;
            description "The directionality of the ForwardingConstruct. 
Is applicable to simple ForwardingConstructs where all FcPorts are BIDIRECTIONAL (the ForwardingConstruct will be BIDIRECTIONAL) or UNIDIRECTIONAL (the ForwardingConstruct will be UNIDIRECTIONAL). 
Is not present in more complex cases.";
        }
    }
    list NetworkControlDomain {
        key 'id uuid';
        status current;
        config true;
        ordered-by system;
        uses CoreModel-CoreFoundationModule-SuperClassesAndCommonPackages:G_GlobalClass;
        leaf-list _forwardingDomainRefList {
            description "The FDs accessible via the NCD.";
            ordered-by system;
            type leafref {
                path '/CoreModel-CoreNetworkModule-ObjectClasses:ForwardingDomain/CoreModel-CoreNetworkModule-ObjectClasses:uuid';
            }
        }
        leaf-list _linkRefList {
            description "The links accessible in the scope of the NCD. 
The domain is bounded by off-network links.";
            ordered-by system;
            type leafref {
                path '/CoreModel-CoreNetworkModule-ObjectClasses:Link/CoreModel-CoreNetworkModule-ObjectClasses:uuid';
            }
        }
        list _networkElementRefList {
            description "The network elements within the scope of the NCD where each NE is within one and only one domain.";
            key 'id uuid';
            config true;
            ordered-by system;
            uses G_NetworkElement;
        }
        leaf id {
            type string;
        }
        max-elements 2;
        min-elements 1;
    }
    list Link {
        key 'uuid';
        config true;
        ordered-by system;
        uses G_Link;
    }
    grouping G_Link {
        uses CoreModel-CoreFoundationModule-SuperClassesAndCommonPackages:G_GlobalClass;
        uses G_TopologicalEntity;
        leaf-list layerProtocolNameList {
            description "The Link can support multiple transport layer protocols via the associated LTP object. 
For implementation optimization, where appropriate, multiple layer-specific links can be merged and represented as a single Link instance as the Link can represent a list of layer protocols.
A link may support different layer protocols at each Port when it is a transitional link.";
            ordered-by system;
            type CoreModel-CoreNetworkModule-TypeDefinitions:LayerProtocolName;
            min-elements 1;
        }
        leaf-list _fdRefList {
            description "The Link associates with two or more FDs. 
This association provides a direct summarization of the association via LinkPort and LTP.";
            ordered-by system;
            type leafref {
                path '/CoreModel-CoreNetworkModule-ObjectClasses:ForwardingDomain/CoreModel-CoreNetworkModule-ObjectClasses:uuid';
            }
            min-elements 2;
        }
        list _linkPortList {
            description "The association of the Link to LTPs is made via LinkPort (essentially the ports of the Link).";
            key 'id';
            config true;
            ordered-by system;
            uses G_LinkPort;
            min-elements 2;
        }
        leaf _linkSpecRef {
            type leafref {
                path '/CoreModel-CoreModelEnhancements-ProfilesTemplatesAndSpecificationsModule:LinkSpec/CoreModel-CoreModelEnhancements-ProfilesTemplatesAndSpecificationsModule:id';
            }
            description "References the specification that describes the capability and internal structure of of the Link (e.g. asymmetric flows between points).
The specification allows interpretation of LinkPort role and switch configurations etc.
See also ForwardingConstruct.";
        }
        leaf-list _aggregatedLink {
            description "A link may formed from subordinate links (similar FD formations from subordiate FDs). This association is intended to cover concepts such as serial compound links. ";
            ordered-by system;
            type leafref {
                path '/Link/uuid';
            }
        }
        leaf linkDirection {
            type CoreModel-CoreNetworkModule-TypeDefinitions:ForwardingDirection;
            description "The directionality of the Link. 
Is applicable to simple Links where all LinkPorts are BIDIRECTIONAL (the Link will be BIDIRECTIONAL) or UNIDIRECTIONAL (the Link will be UNIDIRECTIONAL). 
Is not present in more complex cases.";
        }
    }
    list NetworkElement {
        key 'id uuid';
        config true;
        ordered-by system;
        uses G_NetworkElement;
    }
    grouping G_NetworkElement {
        status deprecated;
        uses CoreModel-CoreFoundationModule-SuperClassesAndCommonPackages:G_GlobalClass;
        list _fdRefList {
            description "Represents the FD that is completely within the boundary of the NE.
At a low level of recursion, an FD (within a network element (NE)) represents a switch matrix (i.e., a fabric). 
Note that an NE can encompass multiple switch matrices (FDs) and the FD representing the switch matrix can be further partitioned.
Where an FD is referenced by the NeEncompassesFd association, any FDs that it encompasses (i.e., that are associated with it by HigherLevelFdEncompassesLowerLevelFds), must also be encompassed by the NE and hence must have the NeEncompassesFd association.
";
            key 'uuid';
            config true;
            ordered-by system;
            uses G_ForwardingDomain;
        }
        leaf-list _ltppList {
            description "OBSOLETE. Was reference to LtpPool. The pool has now been subsumed into the LTP.
This will be deleted in the next release.";
            ordered-by system;
            type string;
        }
        list _ltpRefList {
            description "An NE has associated LTPs that are at its boundary.
The NeEncompassesFd association occurs for FDs that are within the bounds of the NetworkElement definition such that the FD is bounded by LTPs, all of which are on the boundary of the NetworkElement or are within the NetworkElement. 
An LTP can be independent of an NE.";
            key 'uuid';
            config true;
            ordered-by system;
            uses G_LogicalTerminationPoint;
        }
        leaf id {
            type string;
        }
    }
    grouping G_SdnController {
        status current;
        uses CoreModel-CoreFoundationModule-SuperClassesAndCommonPackages:G_GlobalClass;
    }
    list LayerProtocol {
        key 'layerProtocolName';
        config true;
        ordered-by system;
        uses G_LayerProtocol;
    }
    grouping G_LayerProtocol {
        uses CoreModel-CoreFoundationModule-SuperClassesAndCommonPackages:G_LocalClass;
        leaf layerProtocolName {
            type CoreModel-CoreNetworkModule-TypeDefinitions:LayerProtocolName;
            description "Indicate the specific layer-protocol described by the LayerProtocol entity.";
        }
        leaf _lpSpec {
            type leafref {
                path '/CoreModel-CoreModelEnhancements-ProfilesTemplatesAndSpecificationsModule:LpSpec/CoreModel-CoreModelEnhancements-ProfilesTemplatesAndSpecificationsModule:id';
            }
            description "The LpSpec identifies the interna structure of the LP explaining internal flexibilities, degree of termination and degree of adaptation on both client and server side.";
        }
        leaf configuredClientCapacity {
            type string;
            description "Provides a summarized view of the client capacity that is configurable for use.
Note the cleint LTP association should provide all necessary detail hence this attribute is questionable.";
        }
        leaf lpDirection {
            type CoreModel-CoreNetworkModule-TypeDefinitions:TerminationDirection;
            description "The overall directionality of the LP. 
- A BIDIRECTIONAL LP will have some SINK and/or SOURCE flowss.
- A SINK LP can only contain elements with SINK flows or CONTRA_DIRECTION_SOURCE flows
- A SOURCE LP can only contain SOURCE flows or CONTRA_DIRECTION_SINK flows";
        }
        leaf terminationState {
            type string;
            description "Indicates whether the layer is terminated and if so how.";
        }
    }
    list LogicalTerminationPoint {
        key 'uuid';
        config true;
        ordered-by system;
        uses G_LogicalTerminationPoint;
    }
    grouping G_LogicalTerminationPoint {
        uses CoreModel-CoreFoundationModule-SuperClassesAndCommonPackages:G_GlobalClass;
        leaf-list _serverLtpRefList {
            description "References contained LTPs representing servers of this LTP in an inverse multiplexing configuration (e.g. VCAT).";
            ordered-by system;
            type leafref {
                path '/LogicalTerminationPoint/uuid';
            }
        }
        leaf-list _clientLtpRefList {
            description "References contained LTPs representing client traffic of this LTP for normal cases of multiplexing.";
            ordered-by system;
            type leafref {
                path '/LogicalTerminationPoint/uuid';
            }
        }
        list _lpList {
            description "Ordered list of LayerProtocols that this LTP is comprised of where the first entry in the list is the lowest server layer (e.g. physical)";
            key 'layerProtocolName';
            config true;
            ordered-by system;
            uses G_LayerProtocol;
            min-elements 1;
        }
        leaf _connectedLtpRef {
            type leafref {
                path '/LogicalTerminationPoint/uuid';
            }
            description "Applicable in a simple context where two LTPs are associated via a non-adjustable enabled forwarding.
Reduces clutter removing the need for two additional LTPs and an FC with a pair of FcPorts.";
        }
        leaf _peerLtpRef {
            type leafref {
                path '/LogicalTerminationPoint/uuid';
            }
            description "References contained LTPs representing the reversal of orientation of flow where two LTPs are associated via a non-adjustable enabled forwarding and where the referenced LTP is fully dependent on the this LTP.";
        }
        leaf _ltpSpec {
            type leafref {
                path '/CoreModel-CoreModelEnhancements-ProfilesTemplatesAndSpecificationsModule:LtpSpec/CoreModel-CoreModelEnhancements-ProfilesTemplatesAndSpecificationsModule:id';
            }
            description "The specification of the LTP defines internal structure of the LTP.
The specification allows interpretation of organisatoon of LPs making up the LTP and also identifies which inter-LTP associations are valid.";
        }
        leaf-list physicalPortReference {
            description "One or more text labels for the unmodelled physical port associated with the LTP.
In many cases there is no associated physical port";
            ordered-by system;
            type string;
        }
        leaf-list _ltpRefList {
            description "References one or more LTPs in other views that represent this LTP. 
The referencing LTP is the rovider of capability.";
            ordered-by system;
            type leafref {
                path '/LogicalTerminationPoint/uuid';
            }
        }
        leaf ltpDirection {
            type CoreModel-CoreNetworkModule-TypeDefinitions:TerminationDirection;
            description "The overall directionality of the LTP. 
- A BIDIRECTIONAL LTP must have at least some LPs that are BIDIRECTIONAL but may also have some SINK and/or SOURCE LPs.
- A SINK LTP can only contain SINK LPs
- A SOURCE LTP can only contain SOURCE LPs";
        }
    }
    container FcRouteList {
        list FcRoute {
            key 'id';
            config true;
            ordered-by system;
            uses G_FcRoute;
        }
    }
    grouping G_FcRoute {
        list ForwardingConstruct {
            key "uuid";
            uses G_ForwardingConstruct;
        }
        leaf id {
            type string;
        }
    }
    list LinkPort {
        key 'id';
        config true;
        ordered-by system;
        uses G_LinkPort;
    }
    grouping G_LinkPort {
        uses CoreModel-CoreFoundationModule-SuperClassesAndCommonPackages:G_LocalClass;
        leaf _ltpp {
            type string;
            description "OBSOLETE. Was reference to LtpPool. The pool has now been subsumed into the LTP.
This will be deleted in the next release.";
        }
        leaf-list _ltpRefList {
            description "The LinkPort may be associated with more than one LTP when the LinkPort is bidirectional and the LTPs are unidirectional.
Multiple Ltp
- Bidirectional LinkPort to two Uni Ltps
Zero Ltp
- BreakBeforeMake transition
- Planned Ltp not yet in place
- Off-network LTP referenced through other mechanism";
            ordered-by system;
            type leafref {
                path '/CoreModel-CoreNetworkModule-ObjectClasses:LogicalTerminationPoint/CoreModel-CoreNetworkModule-ObjectClasses:uuid';
            }
        }
        leaf role {
            type CoreModel-CoreNetworkModule-TypeDefinitions:PortRole;
            description "Each LinkPort of the Link has a role (e.g., symmetric, hub, spoke, leaf, root)  in the context of the Link with respect to the Link function. ";
        }
        leaf offNetworkAddress {
            type string;
            description "A freeform opportunity to express a reference for an Port of the Link that is not outside the scope of the control domain.
This attribute is expected to convey a foreign identifier/name/address or a shared reference for some mid-span point at the boundary between two administrative domains.
This attribute is used when an LTP cannot be referenced.";
        }
        leaf linkPortDirection {
            type CoreModel-CoreNetworkModule-TypeDefinitions:PortDirection;
            description "The orientation of defined flow at the LinkPort.";
        }
        leaf id {
            type string;
        }
    }
    grouping G_TransferCost_Pac {
        list costCharacteristicList {
            description "The list of costs where each cost relates to some aspect of the TopologicalEntity.";
            key 'costName';
            config true;
            ordered-by system;
            uses CoreModel-CoreNetworkModule-TypeDefinitions:G_CostCharacteristics;
            min-elements 1;
        }
    }
    grouping G_RiskParameter_Pac {
        list riskCharacteristicList {
            description "A list of risk characteristics for consideration in an analysis of shared risk. Each element of the list represents a specific risk consideration.";
            key 'riskCharacteristicName';
            config true;
            ordered-by system;
            uses CoreModel-CoreNetworkModule-TypeDefinitions:G_RiskCharacteristic;
            min-elements 1;
        }
    }
    grouping G_LayerProtocolTransition_Pac {
        leaf-list transitionedLayerProtocolList {
            description "Provides the ordered structure of layer protocol transitions encapsulated in the TopologicalEntity. The ordering relates to the LinkPort role.";
            ordered-by system;
            type string;
            min-elements 1;
        }
        leaf-list _ltpRefList {
            description "Lists the LTPs that define the layer protocol transition of the transitional link.";
            ordered-by system;
            type leafref {
                path '/CoreModel-CoreNetworkModule-ObjectClasses:LogicalTerminationPoint/CoreModel-CoreNetworkModule-ObjectClasses:uuid';
            }
            min-elements 1;
        }
        leaf id {
            type string;
        }
    }
    feature feature1 {
        description "Present if jitterCharacteristics information is relevant to usage and statement can be made that applies equally to all flows that can be supported by the TopologicalEntity.
            Note that if jitterCharacteristics is relevant but consistent ststement cannot be made then the TopologicalEntity should be described in terms of subordinate parts against which coherent statements can be made.
            Note that this only applies to TDM.";
    }
    feature feature2 {
        description "Present if wanderCharacteristics information is relevant to usage and statement can be made that applies equally to all flows that can be supported by the TopologicalEntity.
            Note that if wanderCharacteristics is relevant but consistent ststement cannot be made then the TopologicalEntity should be described in terms of subordinate parts against which coherent statements can be made.
            Note that this only applies to TDM.";
    }
    feature feature3 {
        description "Present if queuingLatencyCharacteristics information is relevant to usage and statement can be made that applies equally to all flows that can be supported by the TopologicalEntity.
            There may be more than one instance if the queuing behavior depends upon traffic properties.
            Note that if queuingLatencyCharacteristics is relevant but consistent statement cannot be made then the TopologicalEntity should be described in terms of subordinate parts against which coherent statements can be made.
            Note that this only applies to packet system.";
    }
    grouping G_TransferTiming_Pac {
        leaf fixedLatencyCharacteristic {
            type string;
            description "A TopologicalEntity suffers delay caused by the realization of the servers (e.g. distance related; FEC encoding etc.) along with some client specific processing. This is the total average latency effect of the TopologicalEntity";
        }
        leaf jitterCharacteristic {
            type string;
            description "High frequency deviation from true periodicity of a signal and therefore a small high rate of change of transfer latency.
Applies to TDM systems (and not packet).";
            if-feature feature1;
        }
        leaf wanderCharacteristic {
            type string;
            description "Low frequency deviation from true periodicity of a signal and therefore a small low rate of change of transfer latency.
Applies to TDM systems (and not packet).";
            if-feature feature2;
        }
        list queuingLatencyList {
            description "The effect on the latency of a queuing process. This only has significant effect for packet based systems and has a complex characteristic.";
            key 'id';
            config true;
            ordered-by system;
            uses CoreModel-CoreNetworkModule-TypeDefinitions:G_QueuingLatency;
            if-feature feature3;
        }
    }
    feature feature4 {
        description "Present if errorCharacteristics information is relevant to usage and statement can be made that applies equally to all flows that can be supported by the TopologicalEntity.
            Note that if errorCharacteristics is relevant but consistent ststement cannot be made then the TopologicalEntity should be described in terms of subordinate parts against which coherent statements can be made.
            Note that this only applies to TDM.";
    }
    feature feature5 {
        description "Present if lossCharacteristics information is relevant to usage and statement can be made that applies equally to all flows that can be supported by the TopologicalEntity.
            Note that if lossCharacteristics is relevant but consistent ststement cannot be made then the TopologicalEntity should be described in terms of subordinate parts against which coherent statements can be made.
            Note that this only applies to packet systems.";
    }
    feature feature6 {
        description "Present if repeatCharacteristics information is relevant to usage and statement can be made that applies equally to all flows that can be supported by the TopologicalEntity.
            Note that if repeatCharacteristics is relevant but consistent ststement cannot be made then the TopologicalEntity should be described in terms of subordinate parts against which coherent statements can be made.
            Note that this primarily applies to packet systemswhere a packet may be delivered more than once (in fault recovery for example). 
            Note that it can also apply to TDM where several frames may  be received twice due to switching in a system with a large differential propagation delay.";
    }
    feature feature7 {
        description "Present if deliveryOrderCharacteristics information is relevant to usage and statement can be made that applies equally to all flows that can be supported by the TopologicalEntity.
            Note that if deliveryOrderCharacteristics is relevant but consistent ststement cannot be made then the TopologicalEntity should be described in terms of subordinate parts against which coherent statements can be made.
            Note that this only applies to packet systems.
            ";
    }
    feature feature8 {
        description "Present if serverIntegrityProcessCharacteristics information is relevant to usage and statement can be made that applies equally to all flows that can be supported by the TopologicalEntity.
            Note that if serverIntegrityProcessCharacteristics is relevant but consistent ststement cannot be made then the TopologicalEntity should be described in terms of subordinate parts against which coherent statements can be made.
            Note that this only applies where the server has some error recovery mechanism alters the characteristics of the link from a normal distribution.";
    }
    grouping G_TransferIntegrity_Pac {
        leaf errorCharacteristic {
            type string;
            description "Describes the degree to which the signal propagated can be errored. 
Applies to TDM systems as the errored signal will be propagated and not packet as errored packets will be discarded.";
            if-feature feature4;
        }
        leaf lossCharacteristic {
            type string;
            description "Describes the acceptable characteristic of lost packets where loss may result from discard due to errors or overflow.
Applies to packet systems and not TDM (as for TDM errored signals are propagated unless grossly errored and overflow/underflow turns into timing slips).";
            if-feature feature5;
        }
        leaf repeatDeliveryCharacteristic {
            type string;
            description "Primarily applies to packet systems where a packet may be delivered more than once (in fault recovery for example). 
It can also apply to TDM where several frames may be received twice due to switching in a system with a large differential propagation delay.";
            if-feature feature6;
        }
        leaf deliveryOrderCharacteristic {
            type string;
            description "Describes the degree to which packets will be delivered out of sequence.
Does not apply to TDM as the TDM protocols maintain strict order.";
            if-feature feature7;
        }
        leaf unavailableTimeCharacteristic {
            type string;
            description "Describes the duration for which there may be no valid signal propagated.";
        }
        leaf serverIntegrityProcessCharacteristic {
            type string;
            description "Describes the effect of any server integrity enhancement process on the characteristics of the TopologicalEntity.";
            if-feature feature8;
        }
    }
    grouping G_TransferCapacity_Pac {
        container totalPotentialCapacity {
            description "An optimistic view of the capacity of the TopologicalEntity assuming that any shared capacity is available to be taken.";
            config true;
            uses CoreModel-CoreNetworkModule-TypeDefinitions:G_Capacity;
        }
        container availableCapacity {
            description "Capacity available to be assigned.";
            config true;
            uses CoreModel-CoreNetworkModule-TypeDefinitions:G_Capacity;
        }
        list capacityAssignedToUserView {
            description "Capacity already assigned";
            key 'id';
            config true;
            ordered-by system;
            uses CoreModel-CoreNetworkModule-TypeDefinitions:G_Capacity;
        }
        leaf capacityInteractionAlgorithm {
            type string;
            description "A reference to an algorithm that describes how various chunks of allocated capacity interact (e.g. when shared)";
        }
    }
    feature feature9 {
        description "Present if risk information is relevant to usage and statement can be made that applies equally to all flows that can be supported by the TopologicalEntity.
            Note that if risk is relevant but consistent ststement cannot be made then the TopologicalEntity should be described in terms of subordinate parts against which coherent statements can be made.";
    }
    feature feature10 {
        description "Present if cost information is relevant to usage and statement can be made that applies equally to all flows that can be supported by the TopologicalEntity.
            Note that if cost is relevant but consistent ststement cannot be made then the TopologicalEntity should be described in terms of subordinate parts against which coherent statements can be made.";
    }
    feature feature11 {
        description "Present if transfer timing information is relevant to usage and statement can be made that applies equally to all flows that can be supported by the TopologicalEntity.
            Note that if transfer timing is relevant but consistent ststement cannot be made then the TopologicalEntity should be described in terms of subordinate parts against which coherent statements can be made.";
    }
    feature feature12 {
        description "Present if transfer capacity information is relevant to usage and statement can be made that applies equally to all flows that can be supported by the TopologicalEntity.
            Note that if transfer capacity is relevant but consistent ststement cannot be made then the TopologicalEntity should be described in terms of subordinate parts against which coherent statements can be made.";
    }
    feature feature13 {
        description "Present if transfer integrity information is relevant to usage and statement can be made that applies equally to all flows that can be supported by the TopologicalEntity.
            Note that if transfer integrity is relevant but consistent ststement cannot be made then the TopologicalEntity should be described in terms of subordinate parts against which coherent statements can be made.";
    }
    feature feature14 {
        description "Present if validation information is relevant to usage and statement can be made that applies equally to all flows that can be supported by the TopologicalEntity.
            Note that if validation is relevant but consistent ststement cannot be made then the TopologicalEntity should be described in terms of subordinate parts against which coherent statements can be made.
            Note that validation may not be possible for the specific layer protocol or in the particular case.";
    }
    feature feature15 {
        description "Present if layer transition information is relevant to usage and statement can be made that applies equally to all flows that can be supported by the TopologicalEntity.
            Note that if layer transiotio is relevant but consistent ststement cannot be made then the TopologicalEntity should be described in terms of subordinate parts against which coherent statements can be made.
            Note that layer transition occurs in a limited number of cases.";
    }
    grouping G_TopologicalEntity {
        container _riskParameter_Pac {
            config true;
            uses G_RiskParameter_Pac;
        }
        container _transferCost_Pac {
            config true;
            uses G_TransferCost_Pac;
        }
        container _transferTiming_Pac {
            config true;
            uses G_TransferTiming_Pac;
        }
        container _transferCapacity_Pac {
            config true;
            uses G_TransferCapacity_Pac;
        }
        container _transferIntegrity_Pac {
            config true;
            uses G_TransferIntegrity_Pac;
        }
        container _validation_Pac {
            config true;
            uses G_Validation_Pac;
        }
        list _layerTransition_Pac {
            key 'id';
            config true;
            ordered-by system;
            uses G_LayerProtocolTransition_Pac;
            if-feature feature15;
        }
    }
    grouping G_Validation_Pac {
        list validationMechanismList {
            description "Provides details of the specific validation mechanism(s) used to confirm the presence of an intended topologicalEntity.";
            key 'id';
            config true;
            ordered-by system;
            uses CoreModel-CoreNetworkModule-TypeDefinitions:G_ValidationMechanism;
            min-elements 1;
        }
    }
    list FcPort {
        key 'id';
        config true;
        ordered-by system;
        uses G_FcPort;
    }
    grouping G_FcPort {
        leaf-list _ltpRefList {
            description "The FcPort may be associated with more than one LTP when the FcPort is bidirectional and the LTPs are unidirectional.
Multiple Ltp
- Bidirectional FcPort to two Uni Ltps
Zero Ltp
- BreakBeforeMake transition
- Planned Ltp not yet in place
- Off-network LTP referenced through other mechanism";
            ordered-by system;
            type leafref {
                path '/CoreModel-CoreNetworkModule-ObjectClasses:LogicalTerminationPoint/CoreModel-CoreNetworkModule-ObjectClasses:uuid';
            }
            max-elements 2;
        }
        leaf role {
            type CoreModel-CoreNetworkModule-TypeDefinitions:PortRole;
            description "Each FcPort of the FC has a role (e.g., working, protection, protected, symmetric, hub, spoke, leaf, root)  in the context of the FC with respect to the FC function. ";
        }
        leaf fcPortDirection {
            type CoreModel-CoreNetworkModule-TypeDefinitions:PortDirection;
            description "The orientation of defined flow at the FcPort.";
        }
        leaf id {
            type string;
        }
    }
    list FcSwitch {
        key 'id';
        config true;
        ordered-by system;
        uses G_FcSwitch;
    }
    grouping G_FcSwitch {
        uses CoreModel-CoreFoundationModule-SuperClassesAndCommonPackages:G_LocalClass;
        leaf holdOffTime {
            type uint64;
            description "This attribute indicates the time, in seconds, between declaration of unacceptable quality of signal on the currently selected FcPort, and the initialization of the protection switching algorithm. ";
        }
        leaf waitToRestoreTime {
            type uint64;
            description "If the protection system is revertive, this attribute specifies the amount of time, in seconds, to wait after the preferred FcPort returns to an acceptable state of operaion (e.g a fault has cleared) before restoring traffic to that preferred FcPort. ";
        }
        leaf protType {
            type CoreModel-CoreNetworkModule-TypeDefinitions:ProtectionType;
            description "Indicates the protection scheme that is used for the ProtectionGroup.";
        }
        leaf operType {
            type CoreModel-CoreNetworkModule-TypeDefinitions:OperType;
            description "This attribute whether or not the protection scheme is revertive or non-revertive. ";
        }
        leaf-list _selectedFcPortRefList {
            description "Indicates which points are selected by the switch.";
            ordered-by system;
            type leafref {
                path '/CoreModel-CoreNetworkModule-ObjectClasses:FcPort/CoreModel-CoreNetworkModule-ObjectClasses:id';
            }
            min-elements 1;
        }
        leaf-list _profileProxyRefList {
            description "Provides a set of predefined values for switch control in place of the direct values avaiable via the FcSwitch or via _configurationAndSwitchControl ";
            ordered-by system;
            type leafref {
                path '/CoreModel-CoreModelEnhancements-FcSwitchEnhancements_Developed:ProfileProxy/CoreModel-CoreModelEnhancements-FcSwitchEnhancements_Developed:id';
            }
        }
        leaf _configurationAndSwitchControlRef {
            type leafref {
                path '/CoreModel-CoreNetworkModule-ObjectClasses:ConfigurationAndSwitchController/CoreModel-CoreNetworkModule-ObjectClasses:id';
            }
            description "A multi-switch controller external to the FcSwitch.
The multi-switch controller coordinates multiple switches in the same FC or across multple FCs";
        }
        container _configurationAndSwitchControl {
            description "A switch controller encapsulated in the FcSwitch.
";
            config true;
            uses G_ConfigurationAndSwitchController;
        }
        leaf id {
            type string;
        }
    }
    list ConfigurationAndSwitchController {
        key 'id';
        config true;
        ordered-by system;
        uses G_ConfigurationAndSwitchController;
    }
    grouping G_ConfigurationAndSwitchController {
        status deprecated;
        leaf SwichRule {
            type string;
            description "A sketch of the presence of complex rules governing the switch behavior.";
        }
        leaf-list _fcSwitchRefList {
            description "The switch being controlled.";
            ordered-by system;
            type leafref {
                path '/CoreModel-CoreNetworkModule-ObjectClasses:FcSwitch/CoreModel-CoreNetworkModule-ObjectClasses:id';
            }
        }
        container _controlParameters {
            description "The control parameters to be aplied if local parameters are used rather than profiles";
            config true;
            uses CoreModel-CoreModelEnhancements-FcSwitchEnhancements_Developed:G_ControlParameters;
        }
        leaf-list _profileProxyRef {
            description "Applied profiles.";
            ordered-by system;
            type leafref {
                path '/CoreModel-CoreModelEnhancements-FcSwitchEnhancements_Developed:ProfileProxy/CoreModel-CoreModelEnhancements-FcSwitchEnhancements_Developed:id';
            }
        }
        leaf id {
            type string;
        }
    }
    list ConfigurationGroup {
        key 'id';
        status deprecated;
        config true;
        list _configurationAndSwitchControlRefList {
            description "A controller operating in the scope defined.";
            key 'id';
            config true;
            ordered-by system;
            uses G_ConfigurationAndSwitchController;
        }
        leaf id {
            type string;
        }
    }
}
