module NRP_Interface-TypeDefinitions-TopologyPacs {
    namespace "uri:onf:NRP_Interface-TypeDefinitions-TopologyPacs";
    prefix NRP_Interface-TypeDefinitions-TopologyPacs;
    revision 2016-04-13{}
    grouping G_CostCharacteristics {
        leaf costName {
            type string;
            description "The cost characteristic will related to some aspect of the TopologicalEntity (e.g. $ cost, routing weight). This aspect will be conveyed by the costName.";
        }
        leaf costValue {
            type string;
            description "The specific cost.";
        }
        leaf costAlgorithm {
            type string;
            description "The cost may vary based upon some properties of the TopologicalEntity. The rules for the variation are conveyed by the costAlgorithm.";
        }
    }
    grouping G_RiskCharacteristic {
        leaf riskCharacteristicName {
            type string;
            description "The name of the risk characteristic. The characteristic may be related to a specific degree of closeness. 
For example a particular characteristic may apply to failures that are localized (e.g. to one side of a road) where as another characteristic may relate to failures that have a broader impact (e.g. both sides of a road that crosses a bridge).
Depending upon the importance of the traffic being routed different risk characteristics will be evaluated.";
        }
        leaf-list riskIdentifierList {
            description "A list of the identifiers of each physical/geographic unit (with the specific risk characteristic) that is related to a segment of the TopologicalEntity.";
            ordered-by system;
            type string;
            min-elements 1;
        }
    }
    grouping G_Capacity {
        leaf totalSize {
            type string;
            description "Total capacity of the TopologicalEntity in MB/s";
        }
        leaf numberOfClientInstances {
            type string;
            description "Where there is some limit to the number of client (e.g. in a channelized case).";
        }
        leaf maximumClientSize {
            type string;
            description "Where a client is of variable capacity but due to some underlying realization the maximum size of the client is smaller than the totalSize.";
        }
        leaf numberingRange {
            type string;
            description "Method for identifying units of capacity via some numbering scheme.";
        }
    }
    grouping G_ValidationMechanism {
        leaf validationMechanism {
            type string;
            description "Name of mechanism used to validate adjacency";
        }
        leaf layerProtocolAdjacencyValidated {
            type string;
            description "State of validatiion";
        }
        leaf validationRobustness {
            type string;
            description "Quality of validation (i.e. how likely is the stated validation to be invalid)";
        }
    }
    grouping G_QueuingLatency {
        leaf trafficProperty {
            type string;
            description "The identifier of the specific traffic property to which the queuing latency applies.";
        }
        leaf latencyForTrafficWithProperty {
            type string;
            description "The specific queuing latency for the traffic property.";
        }
    }
}
