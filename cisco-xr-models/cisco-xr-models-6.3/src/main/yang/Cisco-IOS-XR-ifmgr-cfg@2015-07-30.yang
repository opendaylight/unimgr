module Cisco-IOS-XR-ifmgr-cfg {

  /*** NAMESPACE / PREFIX DEFINITION ***/

  namespace "http://cisco.com/ns/yang/Cisco-IOS-XR-6.3-ifmgr-cfg";


  prefix "ifmgr-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ifmgr package configuration.

     This module contains definitions
     for the following management objects:
       global-interface-configuration: Global scoped configuration
         for interfaces
       interface-configurations: interface configurations

     Copyright (c) 2013-2015 by Cisco Systems, Inc.
     All rights reserved.";

  revision "2015-07-30" {
    description
      "Descriptions updated.";
  }

  revision "2015-01-07" {
    description
      "IOS XR 5.3.1 revision.";
  }

  typedef Interface-mode-enum {
    type enumeration {
      enum default {
        value 0;
        description "Default Interface Mode";
      }
      enum point-to-point {
        value 1;
        description "Point-to-Point Interface Mode";
      }
      enum multipoint {
        value 2;
        description "Multipoint Interface Mode";
      }
      enum l2-transport {
        value 3;
        description "L2 Transport Interface Mode";
      }
    }
    description "Interface mode enum";
  }
  typedef Interface-active {
    type string {
      pattern "(act)|(pre)";
    }
    description "act:The interface is active, pre:Preconfiguration";
  }
  typedef Secondary-admin-state-enum {
    type enumeration {
      enum maintenance {
        value 1;
        description "Maintenance Mode";
      }
    }
    description "Secondary admin state enum";
  }
  typedef Link-status-enum {
    type enumeration {
      enum default {
        value 0;
        description
          "Display link status messages for physical links";
      }
      enum disable {
        value 1;
        description "Disable link status messages";
      }
      enum software-interfaces {
        value 2;
        description
          "Display link status messages for all interfaces";
      }
    }
    description "Link status enum";
  }

  container global-interface-configuration {
    xr:xr-xml-map "ifmgr_cfg:GlobalInterfaceConfiguration";
    description "Global scoped configuration for interfaces";
    leaf link-status {
      xr:xr-xml-map "ifmgr_cfg:LinkStatus";
      xr:xr-cli-map "link-status (disable)|(software-interfaces)|(p"+
        "hysical)|(logical) ";
      type Link-status-enum;
      default "default";
      description "Enable or disable link-status messages";
    }
  }

  container interface-configurations {
    xr:xr-xml-map "ifmgr_cfg:InterfaceConfigurationTable";
    description "interface configurations";

    list interface-configuration {
      xr:xr-xml-map "ifmgr_cfg:InterfaceConfiguration";
      key "active interface-name";
      description "The configuration for an interface";

      container dampening {
        xr:xr-xml-map "ifmgr_cfg:Dampening";
        description
          "Whether this interface's state changes are
          dampened or not";
        leaf args {
          xr:xr-xml-map "ifmgr_cfg:Args";
          type enumeration {
            enum default-values {
              value 0;
              description "Default values";
            }
            enum specify-half-life {
              value 1;
              description "Half Life Specified";
            }
            enum specify-all {
              value 4;
              description
                "All Arguments except Restart Penalty
                Specified";
            }
            enum specify-rp {
              value 5;
              description "All Arguments Specified";
            }
          }
          description "Dampening Arguments";
        }
        leaf half-life {
          xr:xr-xml-map "ifmgr_cfg:HalfLife";
          when "../args = 'specify-half-life' or ../args ="+
            " 'specify-all' or ../args = 'specify-rp'" {
              description
                "../Args = 1 or ../Args = 4 or ../Args = 5";
          }
          type uint32 {
            range "1..45";
          }
          units "minute";
          description "Decay half life (in minutes)";
        }
        leaf reuse-threshold {
          xr:xr-xml-map "ifmgr_cfg:ReuseThreshold";
          when "../args = 'specify-all' or ../args = 'specify-rp'" {
            description "../Args = 4 or ../Args = 5";
          }
          type uint32 {
            range "1..20000";
          }
          description "Reuse threshold";
        }
        leaf suppress-threshold {
          xr:xr-xml-map "ifmgr_cfg:SuppressThreshold";
          when "../args = 'specify-all' or ../args = 'specify-rp'" {
            description "../Args = 4 or ../Args = 5";
          }
          type uint32 {
            range "1..20000";
          }
          description "Suppress threshold";
        }
        leaf suppress-time {
          xr:xr-xml-map "ifmgr_cfg:SuppressTime";
          when "../args = 'specify-all' or ../args = 'specify-rp'" {
            description "../Args = 4 or ../Args = 5";
          }
          type uint32 {
            range "1..255";
          }
          units "minute";
          description "Max suppress time (in minutes)";
        }
        leaf restart-penalty {
          xr:xr-xml-map "ifmgr_cfg:RestartPenalty";
          when "../args = 'specify-rp'" {
            description "../Args = 5";
          }
          type uint32 {
            range "0..20000";
          }
          description "Restart penalty";
        }
      }

      container mtus {
        xr:xr-xml-map "ifmgr_cfg:MTUConfiguration";
        description "The MTU configuration for the interface";

        list mtu {
          xr:xr-xml-map "ifmgr_cfg:MTU";
          xr:xr-cli-map "interface <interface> (point-to-point)|(l2"+
            "transport) mtu <number> ";
          key "owner";
          description "The MTU for the interface";
          leaf owner {
            xr:xr-xml-map "ifmgr_cfg:Owner";
            type xr:Cisco-ios-xr-string;
            description
              "The Owner of the interface - eg. for
              'LoopbackX' main interface this is 'loopback'";
          }
          leaf mtu {
            xr:xr-xml-map "ifmgr_cfg:MTU";
            type uint32 {
              range "64..65535";
            }
            mandatory true;
            description "The MTU value";
          }
        }
      }

      container encapsulation {
        xr:xr-xml-map "ifmgr_cfg:Encapsulation";
        description "The encapsulation on the interface";
        leaf encapsulation {
          xr:xr-xml-map "ifmgr_cfg:Encapsulation";
          type string;
          description "The encapsulation - e.g. hdlc, ppp";
        }
        leaf capsulation-options {
          xr:xr-xml-map "ifmgr_cfg:CapsulationOptions";
          type int32;
          description
            "The options for this capsulation, usually '0'";
        }
      }
      leaf shutdown {
        xr:xr-xml-map "ifmgr_cfg:Shutdown";
        xr:xr-cli-map "interface <interface> (point-to-point)|(l2tr"+
          "ansport) shutdown ";
        type empty;
        description
          "The existence of this configuration indicates
          the interface is shut down";
      }
      leaf interface-virtual {
        xr:xr-xml-map "ifmgr_cfg:InterfaceVirtual";
        type empty;
        description
          "The mode in which an interface is running. The
          existence of this object causes the creation of
          the software virtual/subinterface.";
      }
      leaf secondary-admin-state {
        xr:xr-xml-map "ifmgr_cfg:SecondaryAdminState";
        type Secondary-admin-state-enum;
        description "The secondary admin state of the interface";
      }
      leaf interface-mode-non-physical {
        xr:xr-xml-map "ifmgr_cfg:InterfaceModeNonPhysical";
        type Interface-mode-enum;
        default "default";
        description
          "The mode in which an interface is running. The
          existence of this object causes the creation of
          the software subinterface.";
      }
      leaf bandwidth {
        xr:xr-xml-map "ifmgr_cfg:Bandwidth";
        xr:xr-cli-map "interface <interface> (point-to-point)|(l2tr"+
          "ansport) bandwidth <number> ";
        type int32;
        units "kbit/s";
        description "The bandwidth of the interface in kbps";
      }
      leaf link-status {
        xr:xr-xml-map "ifmgr_cfg:LinkStatus";
        xr:xr-cli-map "interface <interface> (point-to-point)|(l2tr"+
          "ansport) logging events link-status ";
        type empty;
        description
          "Enable interface and line-protocol state change
          alarms";
      }
      leaf description {
        xr:xr-xml-map "ifmgr_cfg:Description";
        type string;
        description "The description of this interface";
      }
      leaf active {
        xr:xr-xml-map "ifmgr_cfg:Active";
        type Interface-active;
        description
          "Whether the interface is active or
          preconfigured";
      }
      leaf interface-name {
        xr:xr-xml-map "ifmgr_cfg:InterfaceName";
        type xr:Interface-name;
        description "The name of the interface";
      }
    }
  }
}
