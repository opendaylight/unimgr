module Cisco-IOS-XR-l2vpn-cfg {

  /*** NAMESPACE / PREFIX DEFINITION ***/

  namespace "http://cisco.com/ns/yang/Cisco-IOS-XR-6.1-l2vpn-cfg";


  prefix "l2vpn-cfg";

  /*** LINKAGE (IMPORTS / INCLUDES) ***/

  import ietf-inet-types { prefix "inet"; }

  import ietf-yang-types { prefix "yang"; }

  import Cisco-IOS-XR-types { prefix "xr"; }

  import Cisco-IOS-XR-ifmgr-cfg { prefix "a1"; }

  import Cisco-IOS-XR-snmp-agent-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR l2vpn package configuration.

     This module contains definitions
     for the following management objects:
       l2vpn: L2VPN configuration
       generic-interface-lists: generic interface lists
       evpn: evpn

     This YANG module augments the
       Cisco-IOS-XR-ifmgr-cfg,
       Cisco-IOS-XR-snmp-agent-cfg
     modules with configuration data.

     Copyright (c) 2013-2015 by Cisco Systems, Inc.
     All rights reserved.";

  revision "2015-11-09" {
    description
      "IOS XR 6.0 revision.";
  }

  typedef Interworking {
    type enumeration {
      enum ethernet {
        value 1;
        description "Ethernet interworking";
      }
      enum ipv4 {
        value 3;
        description "IPv4 interworking";
      }
    }
    description "Interworking";
  }
  typedef L2vpn-capability-mode {
    type enumeration {
      enum high-mode {
        value 1;
        description
          "Compute global capability as the highest node
          capability";
      }
      enum single-mode {
        value 2;
        description "Disable global capability re-computation";
      }
    }
    description "L2vpn capability mode";
  }
  typedef Vpls-id-addr-index {
    type uint32 {
      range "0..32767";
    }
    description "Vpls id addr index";
  }
  typedef Tag-rewrite-range {
    type uint32 {
      range "1..4094";
    }
    description "Tag rewrite range";
  }
  typedef Evpnvpnid-range {
    type uint32 {
      range "1..65534";
    }
    description "Evpnvpnid range";
  }
  typedef Pseudowire-label-range {
    type uint32 {
      range "16..1048575";
    }
    description "Pseudowire label range";
  }
  typedef Bridge-domain-transport-mode {
    type enumeration {
      enum vlan-passthrough {
        value 3;
        description "Vlan tagged passthrough mode";
      }
    }
    description "Bridge domain transport mode";
  }
  typedef Preferred-path {
    type enumeration {
      enum te-tunnel {
        value 2;
        description "TE Tunnel";
      }
      enum ip-tunnel {
        value 3;
        description "IP Tunnel";
      }
      enum tp-tunnel {
        value 4;
        description "TP Tunnel";
      }
    }
    description "Preferred path";
  }
  typedef Rd-addr-index {
    type uint32 {
      range "0..65535";
    }
    description "Rd addr index";
  }
  typedef Vccv-verification {
    type enumeration {
      enum none {
        value 0;
        description "No connectivity verification over VCCV";
      }
      enum lsp-ping {
        value 2;
        description "LSP Ping over VCCV";
      }
    }
    description "Vccv verification";
  }
  typedef L2vpn-mtu-range {
    type uint32 {
      range "64..65535";
    }
    description "L2vpn mtu range";
  }
  typedef Mac-withdraw-behavior {
    type enumeration {
      enum legacy {
        value 1;
        description "MAC Withdrawal sent on state-down (legacy)";
      }
      enum optimized {
        value 2;
        description "Optimized MAC Withdrawal";
      }
    }
    description "Mac withdraw behavior";
  }
  typedef Port-down-flush {
    type enumeration {
      enum port-down-flush {
        value 0;
        description "MAC Port Down Flush";
      }
      enum enable-port-down-flush {
        value 1;
        description "Enable Port Down Flush";
      }
      enum disable-port-down-flush {
        value 2;
        description "Disable Port Down Flush";
      }
    }
    description "Port down flush";
  }
  typedef Storm-control-pps-range {
    type uint32 {
      range "1..160000";
    }
    description "Storm control pps range";
  }
  typedef Type-of-service-mode {
    type enumeration {
      enum none {
        value 0;
        description "Do not reflect the type of service";
      }
      enum reflect {
        value 1;
        description "Reflect the type of service";
      }
    }
    description "Type of service mode";
  }
  typedef Pseudowire-tag-range {
    type uint32 {
      range "1..4094";
    }
    description "Pseudowire tag range";
  }
  typedef Multicast-p2mp-signaling {
    type string {
      pattern "(BGP)";
    }
    description "BGP:BGP Signaling";
  }
  typedef Cedge-range {
    type uint32 {
      range "11..100";
    }
    description "Cedge range";
  }
  typedef Mpls-signaling-protocol {
    type enumeration {
      enum none {
        value 1;
        description "No signaling";
      }
      enum ldp {
        value 4;
        description "LDP";
      }
    }
    description "Mpls signaling protocol";
  }
  typedef Erpaps {
    type enumeration {
      enum interface {
        value 1;
        description "ERP APS type interface";
      }
      enum bridge-domain {
        value 2;
        description "ERP APS type bridge domain";
      }
      enum xconnect {
        value 3;
        description "ERP APS type xconnect";
      }
      enum none {
        value 4;
        description "ERP APS type none";
      }
    }
    description "Erpaps";
  }
  typedef Mac-secure-action {
    type enumeration {
      enum restrict {
        value 1;
        description "MAC Secure Action Restrict";
      }
      enum none {
        value 2;
        description "No Action";
      }
      enum shutdown {
        value 3;
        description "MAC Secure Action Shutdown";
      }
    }
    description "Mac secure action";
  }
  typedef Erp-port {
    type enumeration {
      enum none {
        value 1;
        description "ERP port type none";
      }
      enum virtual {
        value 2;
        description "ERP port type virtual";
      }
      enum interface {
        value 3;
        description "ERP port type interface";
      }
    }
    description "Erp port";
  }
  typedef Resync-threshold-range {
    type uint32 {
      range "5..65535";
    }
    description "Resync threshold range";
  }
  typedef Bgp-route-target-role {
    type enumeration {
      enum both {
        value 0;
        description "Both Import and export roles";
      }
      enum import {
        value 1;
        description "Import role";
      }
      enum export {
        value 2;
        description "Export role";
      }
    }
    description "Bgp route target role";
  }
  typedef Backup-disable {
    type enumeration {
      enum never {
        value 0;
        description "Never";
      }
      enum delay {
        value 1;
        description "Delay seconds";
      }
    }
    description "Backup disable";
  }
  typedef Time-to-live-range {
    type uint32 {
      range "1..255";
    }
    description "Time to live range";
  }
  typedef Multicast-p2mp-transport {
    type string {
      pattern "(RSVP_TE)";
    }
    description "RSVP_TE:RSVP-TE Transport";
  }
  typedef Transport-mode {
    type enumeration {
      enum ethernet {
        value 1;
        description "Ethernet port mode";
      }
      enum vlan {
        value 2;
        description "Vlan tagged mode";
      }
      enum vlan-passthrough {
        value 3;
        description "Vlan tagged passthrough mode";
      }
    }
    description "Transport mode";
  }
  typedef Flow-label-tlv-code {
    type enumeration {
      enum 17 {
        value 4;
        description "Set Flow Label Legacy TLV code (DEPRECATED)";
      }
      enum disable {
        value 8;
        description "Disable Sending Flow Label Legacy TLV";
      }
    }
    description "Flow label tlv code";
  }
  typedef Pseudowire-acid-range {
    type uint32 {
      range "1..4294967295";
    }
    description "Pseudowire acid range";
  }
  typedef Pseudowire-id-range {
    type uint32 {
      range "1..4294967295";
    }
    description "Pseudowire id range";
  }
  typedef Interface-profile {
    type enumeration {
      enum snoop {
        value 1;
        description "Set the snooping";
      }
      enum dhcp-protocol {
        value 2;
        description "disable DHCP protocol";
      }
    }
    description "Interface profile";
  }
  typedef Rpl-role {
    type enumeration {
      enum owner {
        value 1;
        description "ERP RPL owner";
      }
      enum neighbor {
        value 2;
        description "ERP RPL neighbor";
      }
      enum next-neighbor {
        value 3;
        description "ERP RPL next neighbor";
      }
    }
    description "Rpl role";
  }
  typedef Pw-switching-point-tlv {
    type enumeration {
      enum hide {
        value 2;
        description "Hide TLV";
      }
    }
    description "Pw switching point tlv";
  }
  typedef Erpaps-level-range {
    type uint32 {
      range "0..7";
    }
    description "Erpaps level range";
  }
  typedef Storm-control {
    type enumeration {
      enum unicast {
        value 1;
        description "Unknown-unicast Storm Control";
      }
      enum multicast {
        value 2;
        description "Multicast Storm Control";
      }
      enum broadcast {
        value 4;
        description "Broadcast Storm Control";
      }
    }
    description "Storm control";
  }
  typedef L2tp-session-id-range {
    type uint32 {
      range "1..65535";
    }
    description "L2tp session id range";
  }
  typedef Mac-learn {
    type enumeration {
      enum default-learning {
        value 0;
        description "Mac Learning";
      }
      enum enable-learning {
        value 1;
        description "Enable Learning";
      }
      enum disable-learning {
        value 2;
        description "Disable Learning";
      }
    }
    description "Mac learn";
  }
  typedef L2tpv3-sequencing {
    type enumeration {
      enum off {
        value 0;
        description "Sequencing is off";
      }
      enum both {
        value 4;
        description "Sequencing on both transmit and receive side";
      }
    }
    description "L2tpv3 sequencing";
  }
  typedef Veid-range {
    type uint32 {
      range "1..16384";
    }
    description "Veid range";
  }
  typedef Load-balance {
    type enumeration {
      enum source-dest-mac {
        value 1;
        description "Source and Destination MAC hashing";
      }
      enum source-dest-ip {
        value 2;
        description "Source and Destination IP hashing";
      }
      enum pseudowire-label {
        value 4;
        description "PW Label hashing";
      }
    }
    description "Load balance";
  }
  typedef L2tp-signaling-protocol {
    type enumeration {
      enum none {
        value 1;
        description "No signaling";
      }
      enum l2tpv3 {
        value 2;
        description "L2TPv3";
      }
    }
    description "L2tp signaling protocol";
  }
  typedef L2vpn-verification {
    type enumeration {
      enum enable {
        value 1;
        description "enable verification";
      }
      enum disable {
        value 2;
        description "disable verification";
      }
    }
    description "L2vpn verification";
  }
  typedef Max-path-mtu-range {
    type uint32 {
      range "68..65535";
    }
    description "Max path mtu range";
  }
  typedef Interface-traffic-flood {
    type enumeration {
      enum traffic-flooding {
        value 0;
        description "Traffic flooding";
      }
      enum enable-flooding {
        value 1;
        description "Enable Flooding";
      }
      enum disable-flooding {
        value 2;
        description "Disable flooding";
      }
    }
    description "Interface traffic flood";
  }
  typedef Pbbvid-range {
    type uint32 {
      range "1..4094";
    }
    description "Pbbvid range";
  }
  typedef L2tp-cookie-value-range {
    type uint32 {
      range "0..4294967295";
    }
    description "L2tp cookie value range";
  }
  typedef L2-encapsulation {
    type enumeration {
      enum vlan {
        value 4;
        description "Vlan tagged mode";
      }
      enum ethernet {
        value 5;
        description "Ethernet port mode";
      }
    }
    description "L2 encapsulation";
  }
  typedef L2vpn-logging {
    type enumeration {
      enum enable {
        value 1;
        description "enable logging";
      }
      enum disable {
        value 2;
        description "disable logging";
      }
    }
    description "L2vpn logging";
  }
  typedef Mac-aging-range {
    type uint32 {
      range "300..30000";
    }
    description "Mac aging range";
  }
  typedef Vpls-id-as-index {
    type uint32 {
      range "0..4294967295";
    }
    description "Vpls id as index";
  }
  typedef Pseudowire-gbl-id-range {
    type uint32 {
      range "1..4294967295";
    }
    description "Pseudowire gbl id range";
  }
  typedef Rdas-index {
    type uint32 {
      range "0..4294967295";
    }
    description "Rdas index";
  }
  typedef L2tp-cookie-size {
    type enumeration {
      enum zero {
        value 0;
        description "Cookie size is zero bytes";
      }
      enum four {
        value 4;
        description "Cookie size is four bytes";
      }
      enum eight {
        value 8;
        description "Cookie size is eight bytes";
      }
    }
    description "L2tp cookie size";
  }
  typedef Mpls-sequencing {
    type enumeration {
      enum off {
        value 0;
        description "Sequencing is off";
      }
      enum transmit {
        value 1;
        description "Sequencing on transmit side";
      }
      enum receive {
        value 2;
        description "Sequencing on receive side";
      }
      enum both {
        value 4;
        description "Sequencing on both transmit and receive side";
      }
    }
    description "Mpls sequencing";
  }
  typedef Erp-instance-range {
    type uint32 {
      range "1..2";
    }
    description "Erp instance range";
  }
  typedef Pw-redundancy-initial-delay-range {
    type uint32 {
      range "0..120";
    }
    description "Pw redundancy initial delay range";
  }
  typedef Vpls-id-as-range {
    type uint32 {
      range "1..65535";
    }
    description "Vpls id as range";
  }
  typedef Rdas-range {
    type uint32 {
      range "1..4294967295";
    }
    description "Rdas range";
  }
  typedef Bridge-bd-mtu-range {
    type uint32 {
      range "46..65535";
    }
    description "Bridge bd mtu range";
  }
  typedef Backup-disable-delay-range {
    type uint32 {
      range "0..180";
    }
    description "Backup disable delay range";
  }
  typedef Storm-control-kbps-range {
    type uint32 {
      range "64..1280000";
    }
    description "Storm control kbps range";
  }
  typedef Mac-limit-action {
    type enumeration {
      enum none {
        value 0;
        description "No action";
      }
      enum flood {
        value 1;
        description "Flood Mac Limit Action";
      }
      enum no-flood {
        value 2;
        description "NoFlood Mac Limit Action";
      }
      enum shutdown {
        value 3;
        description "Shutdown Mac Limit Action";
      }
    }
    description "Mac limit action";
  }
  typedef Erp-port1 {
    type enumeration {
      enum port0 {
        value 0;
        description "ERP main port 0";
      }
      enum port1 {
        value 1;
        description "ERP main port 1";
      }
    }
    description "Erp port1";
  }
  typedef Mac-notification {
    type enumeration {
      enum no-notif {
        value 0;
        description "No_Notification Trap";
      }
      enum syslog {
        value 1;
        description "syslog message";
      }
      enum trap {
        value 2;
        description "Snmp Trap";
      }
      enum syslog-snmp {
        value 3;
        description "Syslog_snmp Trap";
      }
    }
    description "Mac notification";
  }
  typedef Control-word {
    type enumeration {
      enum enable {
        value 1;
        description "Enable control word";
      }
      enum disable {
        value 2;
        description "Disable control word";
      }
    }
    description "Control word";
  }
  typedef Bgp-route-distinguisher {
    type enumeration {
      enum auto {
        value 1;
        description "RD automatically assigned";
      }
      enum two-byte-as {
        value 2;
        description "RD in 2 byte AS:nn format";
      }
      enum four-byte-as {
        value 3;
        description "RD in 4 byte AS:nn format";
      }
      enum ipv4-address {
        value 4;
        description "RD in IpV4address";
      }
    }
    description "Bgp route distinguisher";
  }
  typedef Bgp-route-target-format {
    type enumeration {
      enum none {
        value 0;
        description "No route target";
      }
      enum two-byte-as {
        value 1;
        description "2 Byte AS:nn format";
      }
      enum four-byte-as {
        value 2;
        description "4 byte AS:nn format";
      }
      enum ipv4-address {
        value 3;
        description "IP:nn format";
      }
    }
    description "Bgp route target format";
  }
  typedef Vedge-range {
    type uint32 {
      range "11..100";
    }
    description "Vedge range";
  }
  typedef Vpnid-range {
    type uint32 {
      range "1..4294967295";
    }
    description "Vpnid range";
  }
  typedef Ldp-vpls-id {
    type enumeration {
      enum two-byte-as {
        value 10;
        description "VPLS-ID in 2 byte AS:nn format";
      }
      enum ipv4-address {
        value 266;
        description "VPLS-ID in IPv4 IP:nn format";
      }
    }
    description "Ldp vpls id";
  }
  typedef Ce-id-range {
    type uint32 {
      range "1..16384";
    }
    description "Ce id range";
  }
  typedef Mac-aging {
    type enumeration {
      enum absolute {
        value 1;
        description "Absolute aging type";
      }
      enum inactivity {
        value 2;
        description "Inactivity aging type";
      }
    }
    description "Mac aging";
  }
  typedef Mac-limit-range {
    type uint32 {
      range "0..4294967295";
    }
    description "Mac limit range";
  }
  typedef Pbbisid-range {
    type uint32 {
      range "256..16777214";
    }
    description "Pbbisid range";
  }
  typedef Type-of-service-range {
    type uint32 {
      range "0..255";
    }
    description "Type of service range";
  }
  typedef Flow-label-load-balance {
    type enumeration {
      enum off {
        value 0;
        description "Flow Label load balance is off";
      }
      enum receive {
        value 1;
        description "Delete Flow Label on receive side";
      }
      enum transmit {
        value 2;
        description "Insert Flow Label on transmit side";
      }
      enum both {
        value 3;
        description
          "Insert/Delete  Flow Label on transmit/receive
          side";
      }
    }
    description "Flow label load balance";
  }

  grouping STORM-CONTROL-UNIT {
    description
      "Common node of bd-storm-control,
      bdac-storm-control-type, bdpw-storm-control-type";

    container storm-control-unit {
      xr:xr-xml-map "l2vpn_cfg:StormControlUnit";
      description "Specify units for Storm Control Configuration";
      leaf kbits-per-sec {
        xr:xr-xml-map "l2vpn_cfg:KbitsPerSec";
        type Storm-control-kbps-range;
        units "kbit/s";
        description
          "Kilobits Per Second, PktsPerSec and KbitsPerSec
          cannot be configured together";
      }
      leaf pkts-per-sec {
        xr:xr-xml-map "l2vpn_cfg:PktsPerSec";
        type Storm-control-pps-range;
        units "packet/s";
        description
          "Packets Per Second, PktsPerSec and KbitsPerSec
          cannot be configured together";
      }
    }
  }

  grouping EVPN-ROUTE-DISTINGUISHER {
    description
      "Common node of evpnbgp-auto-discovery,
      evpnevibgp-auto-discovery, pw-routing-bgp";

    container evpn-route-distinguisher {
      xr:xr-xml-map "l2vpn_cfg:EVPNRouteDistinguisher";
      description "Route Distinguisher";
      leaf type {
        xr:xr-xml-map "l2vpn_cfg:Type";
        type Bgp-route-distinguisher;
        description "Router Distinguisher Type";
      }
      leaf as {
        xr:xr-xml-map "l2vpn_cfg:AS";
        when "../type = 'two-byte-as' or ../type = 'four-byte-as'" {
          description "../Type = TwoByteAS or ../Type = FourByteAS";
        }
        type Rdas-range;
        description "Two byte or 4 byte AS number";
      }
      leaf as-index {
        xr:xr-xml-map "l2vpn_cfg:ASIndex";
        when "../type = 'two-byte-as' or ../type = 'four-byte-as'" {
          description "../Type = TwoByteAS or ../Type = FourByteAS";
        }
        type Rdas-index;
        description "AS:nn (hex or decimal format)";
      }
      leaf address {
        xr:xr-xml-map "l2vpn_cfg:Address";
        when "../type = 'ipv4-address'" {
          description "../Type = IPV4Address";
        }
        type inet:ipv4-address-no-zone;
        description "IPV4 address";
      }
      leaf addr-index {
        xr:xr-xml-map "l2vpn_cfg:AddrIndex";
        when "../type = 'ipv4-address'" {
          description "../Type = IPV4Address";
        }
        type Rd-addr-index;
        description "Addr index";
      }
    }
  }

  container l2vpn {
    xr:xr-xml-map "l2vpn_cfg:L2VPN";
    description "L2VPN configuration";

    container pw-routing {
      xr:xr-xml-map "l2vpn_cfg:PWRouting";
      description "Pseudowire-routing attributes";

      container pw-routing-bgp {
        xr:xr-xml-map "l2vpn_cfg:PWRoutingBGP";
        description
          "Enable Autodiscovery BGP Pseudowire-routing BGP";
        leaf enable {
          xr:xr-xml-map "l2vpn_cfg:Enable";
          type empty;
          description "Enable Autodiscovery BGP";
        }
        uses EVPN-ROUTE-DISTINGUISHER;
      }
      leaf pw-routing-global-id {
        xr:xr-xml-map "l2vpn_cfg:PWRoutingGlobalID";
        xr:xr-cli-map "l2vpn pw-routing global-id <number> ";
        type Pseudowire-gbl-id-range;
        description "Pseudowire-routing Global ID";
      }
    }

    container neighbor {
      xr:xr-xml-map "l2vpn_cfg:Neighbor";
      description "L2VPN neighbor submode";
      leaf ldp-flap {
        xr:xr-xml-map "l2vpn_cfg:LDPFlap";
        xr:xr-cli-map "l2vpn neighbor all ldp flap ";
        type empty;
        description "Enable targetted LDP session flap action";
      }
    }

    container database {
      xr:xr-xml-map "l2vpn_cfg:Database";
      description "L2VPN databases";

      container g8032-rings {
        xr:xr-xml-map "l2vpn_cfg:G8032RingTable";
        description "List of G8032 Ring";

        list g8032-ring {
          xr:xr-xml-map "l2vpn_cfg:G8032Ring";
          key "g8032-ring-name";
          description "G8032 Ring";

          container erp-port0s {
            xr:xr-xml-map "l2vpn_cfg:ERPPort0Table";
            description "Ethernet ring protection port0";

            list erp-port0 {
              xr:xr-xml-map "l2vpn_cfg:ERPPort0";
              key "interface-name";
              description "Configure ERP main port0";
              leaf monitor {
                xr:xr-xml-map "l2vpn_cfg:Monitor";
                xr:xr-cli-map "l2vpn ethernet ring g8032 <string> p"+
                  "ort0 interface <interface> monitor interface <in"+
                  "terface> ";
                type xr:Interface-name;
                description
                  "Ethernet ring protection port0 monitor";
              }
              leaf interface-name {
                xr:xr-xml-map "l2vpn_cfg:InterfaceName";
                type xr:Interface-name;
                description "Port0 interface";
              }
            }
          }

          container erp-instances {
            xr:xr-xml-map "l2vpn_cfg:ERPInstanceTable";
            description "List of ethernet ring protection instance";

            list erp-instance {
              xr:xr-xml-map "l2vpn_cfg:ERPInstance";
              key "erp-instance-id";
              description "Ethernet ring protection instance";

              container rpl {
                xr:xr-xml-map "l2vpn_cfg:RPL";
                description "Ring protection link";
                leaf port {
                  xr:xr-xml-map "l2vpn_cfg:Port";
                  type Erp-port1;
                  description "ERP main port number";
                }
                leaf role {
                  xr:xr-xml-map "l2vpn_cfg:Role";
                  type Rpl-role;
                  description "RPL role";
                }
              }

              container aps {
                xr:xr-xml-map "l2vpn_cfg:APS";
                description "Automatic protection switching";

                container port1 {
                  xr:xr-xml-map "l2vpn_cfg:Port1";
                  description "APS channel for ERP port1";
                  leaf aps-type {
                    xr:xr-xml-map "l2vpn_cfg:APSType";
                    type Erpaps;
                    description "Port1 APS type";
                  }
                  leaf aps-channel {
                    xr:xr-xml-map "l2vpn_cfg:APSChannel";
                    type string;
                    description
                      "Port1 APS channel in the format of
                      InterfaceName, BDName or XconnectName";
                  }
                }
                leaf port0 {
                  xr:xr-xml-map "l2vpn_cfg:Port0";
                  xr:xr-cli-map "port0 interface <interface> ";
                  type string;
                  description
                    "Port0 APS channel in the format of
                    InterfaceName";
                }
                leaf enable {
                  xr:xr-xml-map "l2vpn_cfg:Enable";
                  type empty;
                  description
                    "Enable automatic protection switching";
                }
                leaf level {
                  xr:xr-xml-map "l2vpn_cfg:Level";
                  xr:xr-cli-map "level <number> ";
                  type Erpaps-level-range;
                  description
                    "Automatic protection switching level";
                }
              }
              leaf description {
                xr:xr-xml-map "l2vpn_cfg:Description";
                xr:xr-cli-map "description <string> ";
                type string {
                  length "0..32";
                }
                description
                  "Ethernet ring protection instance
                  description";
              }
              leaf inclusion-list {
                xr:xr-xml-map "l2vpn_cfg:InclusionList";
                xr:xr-cli-map "inclusion-list vlan-ids <string> ";
                type string;
                description
                  "Associates a set of VLAN IDs with the G
                  .8032 instance";
              }
              leaf profile {
                xr:xr-xml-map "l2vpn_cfg:Profile";
                xr:xr-cli-map "profile <string> ";
                type string {
                  length "0..32";
                }
                description
                  "Ethernet ring protection instance profile";
              }
              leaf erp-instance-id {
                xr:xr-xml-map "l2vpn_cfg:ERPInstanceID";
                type Erp-instance-range;
                description "ERP instance number";
              }
            }
          }

          container erp-port1s {
            xr:xr-xml-map "l2vpn_cfg:ERPPort1Table";
            description "Ethernet ring protection port0";

            list erp-port1 {
              xr:xr-xml-map "l2vpn_cfg:ERPPort1";
              must "none or virtual-or-interface" {
                description
                  "None or Virtual-or-Interface must be
                  present.";
              }
              key "erp-port-type";
              description "Ethernet ring protection port1";

              grouping ERP-PORT1-CONTENT {
                description "ERP PORT1 CONTENT";
                leaf monitor {
                  type xr:Interface-name;
                  description
                    "Ethernet ring protection port1 monitor";
                }
              }

              container none {
                xr:xr-xml-map "l2vpn_cfg:Monitor";
                when "../erp-port-type = 'none'" {
                  description "../ERPPortType = None";
                }
                presence "Indicates that this node is configured.";
                description "none";
                uses ERP-PORT1-CONTENT;
              }
              leaf erp-port-type {
                xr:xr-xml-map "l2vpn_cfg:ERPPortType";
                type Erp-port;
                description "Port1 type";
              }

              list virtual-or-interface {
                xr:xr-xml-map "l2vpn_cfg:Monitor";
                when "../erp-port-type = 'virtual' or"+
                  " ../erp-port-type = 'interface'" {
                    description
                      "../ERPPortType = Virtual or .
                      ./ERPPortType = Interface";
                }
                key "interface-name";
                description "virtual or interface";
                leaf interface-name {
                  xr:xr-xml-map "l2vpn_cfg:InterfaceName";
                  type xr:Interface-name;
                  description "Port1 interface";
                }
                uses ERP-PORT1-CONTENT;
              }
            }
          }
          leaf open-ring {
            xr:xr-xml-map "l2vpn_cfg:OpenRing";
            xr:xr-cli-map "l2vpn ethernet ring g8032 <string> open-"+
              "ring ";
            type empty;
            description "Specify the G.8032 instance as open ring";
          }
          leaf exclusion-list {
            xr:xr-xml-map "l2vpn_cfg:ExclusionList";
            xr:xr-cli-map "l2vpn ethernet ring g8032 <string> exclu"+
              "sion-list vlan-ids <string> ";
            type string;
            description
              "Vlan IDs in the format of a-b,c,d,e-f,g
              ,untagged";
          }
          leaf erp-provider-bridge {
            xr:xr-xml-map "l2vpn_cfg:ERPProviderBridge";
            type empty;
            description "Ethernet ring protection provider bridge";
          }
          leaf g8032-ring-name {
            xr:xr-xml-map "l2vpn_cfg:G8032RingName";
            type xr:Cisco-ios-xr-string {
              length "0..32";
            }
            description "Name of the G8032 ring";
          }
        }
      }

      container xconnect-groups {
        xr:xr-xml-map "l2vpn_cfg:XConnectGroupTable";
        description "List of xconnect groups";

        list xconnect-group {
          xr:xr-xml-map "l2vpn_cfg:XConnectGroup";
          key "name";
          description "Xconnect group";

          container p2p-xconnects {
            xr:xr-xml-map "l2vpn_cfg:P2PXConnectTable";
            description "List of point to point xconnects";

            list p2p-xconnect {
              xr:xr-xml-map "l2vpn_cfg:P2PXConnect";
              key "name";
              description "Point to point xconnect";

              container backup-attachment-circuits {
                xr:xr-xml-map "l2vpn_cfg:BackupAttachmentCircuitTab"+
                  "le";
                description "List of backup attachment circuits";

                list backup-attachment-circuit {
                  xr:xr-xml-map "l2vpn_cfg:BackupAttachmentCircuit";
                  key "interface-name";
                  description "Backup attachment circuit";
                  leaf interface-name {
                    xr:xr-xml-map "l2vpn_cfg:InterfaceName";
                    type xr:Interface-name;
                    description
                      "Name of the attachment circuit interface";
                  }
                }
              }

              container pseudowire-evpns {
                xr:xr-xml-map "l2vpn_cfg:PseudowireEvpnTable";
                description "List of EVPN Services";

                list pseudowire-evpn {
                  xr:xr-xml-map "l2vpn_cfg:PseudowireEvpn";
                  key "eviid remote-acid source-acid";
                  description "EVPN P2P Service Configuration";
                  leaf eviid {
                    xr:xr-xml-map "l2vpn_cfg:EVIID";
                    type Evpnvpnid-range;
                    description "Ethernet VPN ID";
                  }
                  leaf remote-acid {
                    xr:xr-xml-map "l2vpn_cfg:RemoteACID";
                    type Pseudowire-acid-range;
                    description "Remote AC ID";
                  }
                  leaf source-acid {
                    xr:xr-xml-map "l2vpn_cfg:SourceACID";
                    type Pseudowire-acid-range;
                    description "Source AC ID";
                  }
                }
              }

              container pseudowires {
                xr:xr-xml-map "l2vpn_cfg:PseudowireTable";
                description "List of pseudowires";

                list pseudowire {
                  must "pseudowire-address or neighbor" {
                    description
                      "pseudowire-address or neighbor must be
                      present.";
                  }
                  key "pseudowire-id";
                  description "Pseudowire configuration";

                  grouping PSEUDOWIRE-CONTENT {
                    description "Content grouping.";

                    container mpls-static-labels {
                      xr:xr-xml-map "l2vpn_cfg:MPLSStaticLabels";
                      description "MPLS static labels";
                      leaf local-static-label {
                        xr:xr-xml-map "l2vpn_cfg:LocalStaticLabel";
                        type Pseudowire-label-range;
                        description "Pseudowire local static label";
                      }
                      leaf remote-static-label {
                        xr:xr-xml-map "l2vpn_cfg:RemoteStaticLabel";
                        type Pseudowire-label-range;
                        description
                          "Pseudowire remote static label";
                      }
                    }

                    container backup-pseudowires {
                      xr:xr-xml-map "l2vpn_cfg:BackupPseudowireTabl"+
                        "e";
                      description "List of pseudowires";

                      list backup-pseudowire {
                        xr:xr-xml-map "l2vpn_cfg:BackupPseudowire";
                        key "neighbor pseudowire-id";
                        description
                          "Backup pseudowire for the cross connect";

                        container backup-mpls-static-labels {
                          xr:xr-xml-map "l2vpn_cfg:BackupMPLSStatic"+
                            "Labels";
                          description "MPLS static labels";
                          leaf local-static-label {
                            xr:xr-xml-map "l2vpn_cfg:LocalStaticLab"+
                              "el";
                            type Pseudowire-label-range;
                            description
                              "Pseudowire local static label";
                          }
                          leaf remote-static-label {
                            xr:xr-xml-map "l2vpn_cfg:RemoteStaticLa"+
                              "bel";
                            type Pseudowire-label-range;
                            description
                              "Pseudowire remote static label";
                          }
                        }
                        leaf backup-pw-class {
                          xr:xr-xml-map "l2vpn_cfg:BackupPWClass";
                          type xr:Cisco-ios-xr-string {
                            length "0..32";
                          }
                          description
                            "PW class template name to use for the
                            backup PW";
                        }
                        leaf neighbor {
                          xr:xr-xml-map "l2vpn_cfg:Neighbor";
                          type inet:ipv4-address-no-zone;
                          description "Neighbor IP address";
                        }
                        leaf pseudowire-id {
                          xr:xr-xml-map "l2vpn_cfg:PseudowireID";
                          type Pseudowire-id-range;
                          description "Pseudowire ID";
                        }
                      }
                    }

                    container l2tp-static-attributes {
                      xr:xr-xml-map "l2vpn_cfg:L2TPStaticAttributes";
                      description "L2TP Static Attributes";

                      container l2tp-remote-cookie {
                        xr:xr-xml-map "l2vpn_cfg:L2TPRemoteCookie";
                        description "L2TP remote cookie";
                        leaf size {
                          xr:xr-xml-map "l2vpn_cfg:Size";
                          type L2tp-cookie-size;
                          description "Remote cookie size";
                        }
                        leaf lower-value {
                          xr:xr-xml-map "l2vpn_cfg:LowerValue";
                          type L2tp-cookie-value-range;
                          description "Lower remote cookie value";
                        }
                        leaf higher-value {
                          xr:xr-xml-map "l2vpn_cfg:HigherValue";
                          type L2tp-cookie-value-range;
                          description "Higher remote cookie value";
                        }
                      }

                      container l2tp-secondary-local-cookie {
                        xr:xr-xml-map "l2vpn_cfg:L2TPSecondaryLocal"+
                          "Cookie";
                        description "L2TP secondary local cookie";
                        leaf size {
                          xr:xr-xml-map "l2vpn_cfg:Size";
                          type L2tp-cookie-size;
                          description "Local cookie size";
                        }
                        leaf lower-value {
                          xr:xr-xml-map "l2vpn_cfg:LowerValue";
                          type L2tp-cookie-value-range;
                          description "Lower local cookie value";
                        }
                        leaf higher-value {
                          xr:xr-xml-map "l2vpn_cfg:HigherValue";
                          type L2tp-cookie-value-range;
                          description "Higher local cookie value";
                        }
                      }

                      container l2tp-local-cookie {
                        xr:xr-xml-map "l2vpn_cfg:L2TPLocalCookie";
                        description "L2TP local cookie";
                        leaf size {
                          xr:xr-xml-map "l2vpn_cfg:Size";
                          type L2tp-cookie-size;
                          description "Local cookie size";
                        }
                        leaf lower-value {
                          xr:xr-xml-map "l2vpn_cfg:LowerValue";
                          type L2tp-cookie-value-range;
                          description "Lower local cookie value";
                        }
                        leaf higher-value {
                          xr:xr-xml-map "l2vpn_cfg:HigherValue";
                          type L2tp-cookie-value-range;
                          description "Higher local cookie value";
                        }
                      }
                      leaf l2tp-remote-session-id {
                        xr:xr-xml-map "l2vpn_cfg:L2TPRemoteSessionI"+
                          "D";
                        type L2tp-session-id-range;
                        description "L2TP remote session ID";
                      }
                      leaf l2tp-local-session-id {
                        xr:xr-xml-map "l2vpn_cfg:L2TPLocalSessionID";
                        type L2tp-session-id-range;
                        description "L2TP local session ID";
                      }
                    }

                    container l2tp-static {
                      xr:xr-xml-map "l2vpn_cfg:L2TPStatic";
                      description
                        "Pseudowire L2TPv3 static configuration";
                      leaf enable {
                        xr:xr-xml-map "l2vpn_cfg:Enable";
                        type empty;
                        description
                          "Enable pseudowire L2TPv3 static
                          configuration";
                      }
                    }
                    leaf tag-impose {
                      xr:xr-xml-map "l2vpn_cfg:TagImpose";
                      type Pseudowire-tag-range;
                      description "Tag Impose vlan tagged mode";
                    }
                    leaf class {
                      xr:xr-xml-map "l2vpn_cfg:Class";
                      type xr:Cisco-ios-xr-string {
                        length "0..32";
                      }
                      description "Name of the pseudowire class";
                    }
                    leaf source-address {
                      xr:xr-xml-map "l2vpn_cfg:SourceAddress";
                      type inet:ip-address-no-zone;
                      description
                        "Value of the Pseudowire source address.
                        Must be IPv6 only.";
                    }
                    leaf bandwidth {
                      xr:xr-xml-map "l2vpn_cfg:Bandwidth";
                      type uint32 {
                        range "0..4294967295";
                      }
                      description "Pseudowire Bandwidth";
                    }
                  }
                  leaf pseudowire-id {
                    xr:xr-xml-map "l2vpn_cfg:PseudowireID";
                    type Pseudowire-id-range;
                    description "Pseudowire ID";
                  }

                  list neighbor {
                    xr:xr-xml-map "l2vpn_cfg:Pseudowire";
                    key "neighbor";
                    description "keys: neighbor";
                    leaf neighbor {
                      xr:xr-xml-map "l2vpn_cfg:Neighbor";
                      type inet:ipv4-address-no-zone;
                      description "Pseudowire IPv4 address";
                    }
                    uses PSEUDOWIRE-CONTENT;
                  }

                  list pseudowire-address {
                    xr:xr-xml-map "l2vpn_cfg:Pseudowire";
                    key "pseudowire-address";
                    description "keys: pseudowire-address";
                    leaf pseudowire-address {
                      xr:xr-xml-map "l2vpn_cfg:PseudowireAddress";
                      type inet:ipv6-address-no-zone;
                      description
                        "Pseudowire IPv6 address. A pseudowire
                        can have only one address: IPv4 or IPv6";
                    }
                    uses PSEUDOWIRE-CONTENT;
                  }
                }
              }

              container monitor-sessions {
                xr:xr-xml-map "l2vpn_cfg:MonitorSessionTable";
                description "List of Monitor session segments";

                list monitor-session {
                  xr:xr-xml-map "l2vpn_cfg:MonitorSession";
                  key "name";
                  description "Monitor session segment";
                  leaf enable {
                    xr:xr-xml-map "l2vpn_cfg:Enable";
                    xr:xr-cli-map "l2vpn xconnect group <string> p2"+
                      "p <string> monitor-session <string> ";
                    type empty;
                    description "Enable monitor session segment ";
                  }
                  leaf name {
                    xr:xr-xml-map "l2vpn_cfg:Name";
                    type xr:Cisco-ios-xr-string {
                      length "0..64";
                    }
                    description "Name of the monitor session";
                  }
                }
              }

              container pseudowire-routeds {
                xr:xr-xml-map "l2vpn_cfg:PseudowireRoutedTable";
                description "List of pseudowire-routed";

                list pseudowire-routed {
                  xr:xr-xml-map "l2vpn_cfg:PseudowireRouted";
                  key "global-id prefix acid sacid";
                  description "Pseudowire configuration";
                  leaf tag-impose {
                    xr:xr-xml-map "l2vpn_cfg:TagImpose";
                    xr:xr-cli-map "tag-impose [vlan <number>] ";
                    type Pseudowire-tag-range;
                    description "Tag Impose vlan tagged mode";
                  }
                  leaf class {
                    xr:xr-xml-map "l2vpn_cfg:Class";
                    xr:xr-cli-map "pw-class <string> ";
                    type xr:Cisco-ios-xr-string {
                      length "0..32";
                    }
                    description "Name of the pseudowire class";
                  }
                  leaf global-id {
                    xr:xr-xml-map "l2vpn_cfg:GlobalID";
                    type Pseudowire-gbl-id-range;
                    description "Target Global ID";
                  }
                  leaf prefix {
                    xr:xr-xml-map "l2vpn_cfg:Prefix";
                    type inet:ipv4-address-no-zone;
                    description "Target Prefix";
                  }
                  leaf acid {
                    xr:xr-xml-map "l2vpn_cfg:ACID";
                    type Pseudowire-acid-range;
                    description "Target AC ID";
                  }
                  leaf sacid {
                    xr:xr-xml-map "l2vpn_cfg:SACID";
                    type Pseudowire-acid-range;
                    description "Source AC ID";
                  }
                }
              }

              container attachment-circuits {
                xr:xr-xml-map "l2vpn_cfg:AttachmentCircuitTable";
                description "List of attachment circuits";

                list attachment-circuit {
                  xr:xr-xml-map "l2vpn_cfg:AttachmentCircuit";
                  key "name";
                  description "Attachment circuit interface";
                  leaf enable {
                    xr:xr-xml-map "l2vpn_cfg:Enable";
                    xr:xr-cli-map "l2vpn xconnect group <string> p2"+
                      "p <string> interface (<interface>)|(<interfa"+
                      "ce>) ";
                    type empty;
                    description
                      "Enable attachment circuit interface";
                  }
                  leaf name {
                    xr:xr-xml-map "l2vpn_cfg:Name";
                    type xr:Interface-name;
                    description
                      "Name of the attachment circuit interface";
                  }
                }
              }
              leaf p2p-description {
                xr:xr-xml-map "l2vpn_cfg:P2PDescription";
                xr:xr-cli-map "l2vpn xconnect group <string> p2p <s"+
                  "tring> description <string> ";
                type xr:Cisco-ios-xr-string {
                  length "0..64";
                }
                description "cross connect description Name";
              }
              leaf interworking {
                xr:xr-xml-map "l2vpn_cfg:Interworking";
                xr:xr-cli-map "l2vpn xconnect group <string> p2p <s"+
                  "tring> interworking (ipv4)|(ethernet) ";
                type Interworking;
                description "Interworking";
              }
              leaf name {
                xr:xr-xml-map "l2vpn_cfg:Name";
                type xr:Cisco-ios-xr-string {
                  length "0..38";
                }
                description "Name of the point to point xconnect";
              }
            }
          }

          container mp2mp-xconnects {
            xr:xr-xml-map "l2vpn_cfg:MP2MPXConnectTable";
            description
              "List of multi point to multi point xconnects";

            list mp2mp-xconnect {
              xr:xr-xml-map "l2vpn_cfg:MP2MPXConnect";
              key "name";
              description "Multi point to multi point xconnect";

              container mp2mp-auto-discovery {
                xr:xr-xml-map "l2vpn_cfg:MP2MPAutoDiscovery";
                description "auto-discovery in this MP2MP";

                container route-distinguisher {
                  xr:xr-xml-map "l2vpn_cfg:RouteDistinguisher";
                  description "Route Distinguisher";
                  leaf type {
                    xr:xr-xml-map "l2vpn_cfg:Type";
                    type Bgp-route-distinguisher;
                    description "Router distinguisher type";
                  }
                  leaf as {
                    xr:xr-xml-map "l2vpn_cfg:AS";
                    when "../type = 'two-byte-as' or ../type ="+
                      " 'four-byte-as'" {
                        description
                          "../Type = TwoByteAS or ../Type =
                          FourByteAS";
                    }
                    type Rdas-range;
                    description "Two byte or 4 byte AS number";
                  }
                  leaf as-index {
                    xr:xr-xml-map "l2vpn_cfg:ASIndex";
                    when "../type = 'two-byte-as' or ../type ="+
                      " 'four-byte-as'" {
                        description
                          "../Type = TwoByteAS or ../Type =
                          FourByteAS";
                    }
                    type Rdas-index;
                    description "AS:nn (hex or decimal format)";
                  }
                  leaf address {
                    xr:xr-xml-map "l2vpn_cfg:Address";
                    when "../type = 'ipv4-address'" {
                      description "../Type = IPV4Address";
                    }
                    type inet:ipv4-address-no-zone;
                    description "IPV4 address";
                  }
                  leaf addr-index {
                    xr:xr-xml-map "l2vpn_cfg:AddrIndex";
                    when "../type = 'ipv4-address'" {
                      description "../Type = IPV4Address";
                    }
                    type Rd-addr-index;
                    description "Addr index";
                  }
                }

                container mp2mp-route-targets {
                  xr:xr-xml-map "l2vpn_cfg:MP2MPRouteTargetTable";
                  description "Route Target";

                  list mp2mp-route-target {
                    xr:xr-xml-map "l2vpn_cfg:MP2MPRouteTarget";
                    must "two-byte-as-or-four-byte-as or"+
                      " ipv4-address" {
                      description
                        "TwoByteAS-or-FourbyteAS or IPV4Address
                        must be present.";
                    }
                    key "role format";
                    description "Name of the Route Target";
                    leaf role {
                      xr:xr-xml-map "l2vpn_cfg:Role";
                      type Bgp-route-target-role;
                      description "Role of the router target type";
                    }
                    leaf format {
                      xr:xr-xml-map "l2vpn_cfg:Format";
                      type Bgp-route-target-format;
                      description "Format of the route target";
                    }

                    list two-byte-as-or-four-byte-as {
                      when "../format = 'two-byte-as' or"+
                        " ../format = 'four-byte-as'" {
                          description
                            "../Format = TwoByteAS or ../Format =
                            FourbyteAS";
                      }
                      key "as as-index";
                      description "two byte as or four byte as";
                      leaf as {
                        xr:xr-xml-map "l2vpn_cfg:AS";
                        type Rdas-range;
                        description "Two byte or 4 byte AS number";
                      }
                      leaf as-index {
                        xr:xr-xml-map "l2vpn_cfg:ASIndex";
                        type Rdas-index;
                        description "AS:nn (hex or decimal format)";
                      }
                    }

                    list ipv4-address {
                      when "../format = 'ipv4-address'" {
                        description "../Format = IPV4Address";
                      }
                      key "address addr-index";
                      description "ipv4 address";
                      leaf address {
                        xr:xr-xml-map "l2vpn_cfg:Address";
                        type inet:ipv4-address-no-zone;
                        description "IPV4 address";
                      }
                      leaf addr-index {
                        xr:xr-xml-map "l2vpn_cfg:AddrIndex";
                        type Rd-addr-index;
                        description "Addr index";
                      }
                    }
                  }
                }

                container mp2mp-signaling-protocol {
                  xr:xr-xml-map "l2vpn_cfg:MP2MPSignalingProtocol";
                  description "signaling protocol in this MP2MP";

                  container flow-label-load-balance {
                    xr:xr-xml-map "l2vpn_cfg:FlowLabelLoadBalance";
                    description
                      "Enable Flow Label based load balancing";
                    leaf flow-label {
                      xr:xr-xml-map "l2vpn_cfg:FlowLabel";
                      type Flow-label-load-balance;
                      description "Flow Label load balance type";
                    }
                    leaf static {
                      xr:xr-xml-map "l2vpn_cfg:Static";
                      type empty;
                      description "Static Flow Label";
                    }
                  }

                  container ceids {
                    xr:xr-xml-map "l2vpn_cfg:CEIDTable";
                    description
                      "Local Customer Edge Identifier Table";

                    list ceid {
                      xr:xr-xml-map "l2vpn_cfg:CEID";
                      key "ce-id";
                      description "Local Customer Edge Identifier ";

                      container remote-ceid-attachment-circuits {
                        xr:xr-xml-map "l2vpn_cfg:RemoteCEIDAttachme"+
                          "ntCircuitTable";
                        description
                          "AC And Remote Customer Edge Identifier
                          Table";

                        list remote-ceid-attachment-circuit {
                          xr:xr-xml-map "l2vpn_cfg:RemoteCEIDAttach"+
                            "mentCircuit";
                          key "name remote-ce-id";
                          description
                            "AC And Remote Customer Edge Identifier";
                          leaf name {
                            xr:xr-xml-map "l2vpn_cfg:Name";
                            type xr:Interface-name;
                            description
                              "The name of the Attachment Circuit";
                          }
                          leaf remote-ce-id {
                            xr:xr-xml-map "l2vpn_cfg:RemoteCeId";
                            type Ce-id-range;
                            description
                              "Remote Customer Edge Identifier";
                          }
                        }
                      }
                      leaf ce-id {
                        xr:xr-xml-map "l2vpn_cfg:CEId";
                        type Ce-id-range;
                        description
                          "Local Customer Edge Identifier";
                      }
                    }
                  }
                  leaf ce-range {
                    xr:xr-xml-map "l2vpn_cfg:CERange";
                    xr:xr-cli-map "ce-range <number> ";
                    type Cedge-range;
                    description "Local Customer Edge Identifier";
                  }
                  leaf enable {
                    xr:xr-xml-map "l2vpn_cfg:Enable";
                    type empty;
                    description "Enable signaling protocol";
                  }
                }
                leaf enable {
                  xr:xr-xml-map "l2vpn_cfg:Enable";
                  type empty;
                  description "Enable auto-discovery";
                }
              }
              leaf mp2mpmtu {
                xr:xr-xml-map "l2vpn_cfg:MP2MPMTU";
                xr:xr-cli-map "l2vpn xconnect group <string> mp2mp "+
                  "<string> mtu <number> ";
                type L2vpn-mtu-range;
                units "byte";
                description
                  "Maximum transmission unit for this MP2MP
                  VPWS instance";
              }
              leaf mp2mp-control-word {
                xr:xr-xml-map "l2vpn_cfg:MP2MPControlWord";
                xr:xr-cli-map "l2vpn xconnect group <string> mp2mp "+
                  "<string> control-word disable ";
                type empty;
                description "Disable control word";
              }
              leaf mp2mpl2-encapsulation {
                xr:xr-xml-map "l2vpn_cfg:MP2MPL2Encapsulation";
                xr:xr-cli-map "l2vpn xconnect group <string> mp2mp "+
                  "<string> l2-encapsulation <enum> ";
                type L2-encapsulation;
                description "Configure Layer 2 Encapsulation";
              }
              leaf mp2mp-interworking {
                xr:xr-xml-map "l2vpn_cfg:MP2MPInterworking";
                xr:xr-cli-map "l2vpn xconnect group <string> mp2mp "+
                  "<string> interworking <enum> ";
                type Interworking;
                description "Interworking";
              }
              leaf mp2mp-shutdown {
                xr:xr-xml-map "l2vpn_cfg:MP2MPShutdown";
                xr:xr-cli-map "l2vpn xconnect group <string> mp2mp "+
                  "<string> shutdown ";
                type empty;
                description "shutdown this MP2MP VPWS instance";
              }
              leaf mp2mpvpn-id {
                xr:xr-xml-map "l2vpn_cfg:MP2MPVPNId";
                xr:xr-cli-map "l2vpn xconnect group <string> mp2mp "+
                  "<string> vpn-id <number> ";
                type Vpnid-range;
                description "VPN Identifier";
              }
              leaf name {
                xr:xr-xml-map "l2vpn_cfg:Name";
                type xr:Cisco-ios-xr-string {
                  length "0..26";
                }
                description
                  "Name of the multi point to multi point
                  xconnect";
              }
            }
          }
          leaf name {
            xr:xr-xml-map "l2vpn_cfg:Name";
            type xr:Cisco-ios-xr-string {
              length "0..32";
            }
            description "Name of the xconnect group";
          }
        }
      }

      container bridge-domain-groups {
        xr:xr-xml-map "l2vpn_cfg:BridgeDomainGroupTable";
        description "List of bridge  groups";

        list bridge-domain-group {
          xr:xr-xml-map "l2vpn_cfg:BridgeDomainGroup";
          key "name";
          description "Bridge group";

          container bridge-domains {
            xr:xr-xml-map "l2vpn_cfg:BridgeDomainTable";
            description "List of Bridge Domain";

            list bridge-domain {
              xr:xr-xml-map "l2vpn_cfg:BridgeDomain";
              key "name";
              description "bridge domain";

              container bd-storm-controls {
                xr:xr-xml-map "l2vpn_cfg:BDStormControlTable";
                description "Storm Control";

                list bd-storm-control {
                  xr:xr-xml-map "l2vpn_cfg:BDStormControl";
                  key "sctype";
                  description "Storm Control Type";
                  leaf sctype {
                    xr:xr-xml-map "l2vpn_cfg:SCType";
                    type Storm-control;
                    description "Storm Control Type";
                  }
                  uses STORM-CONTROL-UNIT;
                }
              }

              container member-vnis {
                xr:xr-xml-map "l2vpn_cfg:MemberVNITable";
                description
                  "Bridge Domain VxLAN Network Identifier
                  Table";

                list member-vni {
                  xr:xr-xml-map "l2vpn_cfg:MemberVNI";
                  key "vni";
                  description
                    "Bridge Domain Member VxLAN Network
                    Identifier ";
                  leaf vni {
                    xr:xr-xml-map "l2vpn_cfg:VNI";
                    type uint32 {
                      range "1..16777215";
                    }
                    description "VxLAN Network Identifier number";
                  }
                }
              }

              container bridge-domain-mac {
                xr:xr-xml-map "l2vpn_cfg:BridgeDomainMAC";
                description "MAC configuration commands";

                container bd-mac-limit {
                  xr:xr-xml-map "l2vpn_cfg:BD_MACLimit";
                  description "MAC-Limit configuration commands";
                  leaf bd-mac-limit-action {
                    xr:xr-xml-map "l2vpn_cfg:BD_MACLimitAction";
                    xr:xr-cli-map "action (flood)|(no-flood)|(shutd"+
                      "own) ";
                    type Mac-limit-action;
                    description
                      "MAC address limit enforcement action";
                  }
                  leaf bd-mac-limit-notif {
                    xr:xr-xml-map "l2vpn_cfg:BD_MACLimitNotif";
                    xr:xr-cli-map "notification (trap)|(both)|(none"+
                      ") ";
                    type Mac-notification;
                    description "Mac Address Limit Notification";
                  }
                  leaf bd-mac-limit-max {
                    xr:xr-xml-map "l2vpn_cfg:BD_MACLimitMax";
                    xr:xr-cli-map "maximum <number> ";
                    type Mac-limit-range;
                    description
                      "Number of MAC addresses after which MAC
                      limit action is taken";
                  }
                }

                container bd-mac-filters {
                  xr:xr-xml-map "l2vpn_cfg:BD_MACFilterTable";
                  description "Filter Mac Address";

                  list bd-mac-filter {
                    xr:xr-xml-map "l2vpn_cfg:BD_MACFilter";
                    key "address";
                    description "Static MAC address";
                    leaf drop {
                      xr:xr-xml-map "l2vpn_cfg:Drop";
                      xr:xr-cli-map "static-address <MAC address> d"+
                        "rop ";
                      type empty;
                      description "MAC address for filtering";
                    }
                    leaf address {
                      xr:xr-xml-map "l2vpn_cfg:Address";
                      type yang:mac-address;
                      description "Static MAC address";
                    }
                  }
                }

                container mac-secure {
                  xr:xr-xml-map "l2vpn_cfg:MACSecure";
                  description "MAC Secure";
                  leaf logging {
                    xr:xr-xml-map "l2vpn_cfg:Logging";
                    xr:xr-cli-map "logging ";
                    type empty;
                    description "MAC Secure Logging";
                  }
                  leaf action {
                    xr:xr-xml-map "l2vpn_cfg:Action";
                    xr:xr-cli-map "action (none)|(shutdown) ";
                    type Mac-secure-action;
                    description "MAC secure enforcement action";
                  }
                  leaf enable {
                    xr:xr-xml-map "l2vpn_cfg:Enable";
                    type empty;
                    description "Enable MAC Secure";
                  }
                }

                container bd-mac-aging {
                  xr:xr-xml-map "l2vpn_cfg:BD_MACAging";
                  description "MAC-Aging configuration commands";
                  leaf bd-mac-aging-type {
                    xr:xr-xml-map "l2vpn_cfg:BD_MACAgingType";
                    xr:xr-cli-map "aging type absolute ";
                    type Mac-aging;
                    description "MAC address aging type";
                  }
                  leaf bd-mac-aging-time {
                    xr:xr-xml-map "l2vpn_cfg:BD_MACAgingTime";
                    xr:xr-cli-map "aging time <number> ";
                    type Mac-aging-range;
                    description "Mac Aging Time";
                  }
                }
                leaf bd-mac-withdraw-relay {
                  xr:xr-xml-map "l2vpn_cfg:BD_MACWithdrawRelay";
                  xr:xr-cli-map "withdraw relay ";
                  type empty;
                  description
                    "Mac withdraw sent from access PW to access
                    PW";
                }
                leaf bd-mac-withdraw-access-pw-disable {
                  xr:xr-xml-map "l2vpn_cfg:BD_MACWithdrawAccessPWDi"+
                    "sable";
                  xr:xr-cli-map "withdraw access-pw disable ";
                  type empty;
                  description "MAC withdraw on Access PW";
                }
                leaf bd-mac-port-down-flush {
                  xr:xr-xml-map "l2vpn_cfg:BD_MACPortDownFlush";
                  xr:xr-cli-map "port-down flush [disable] ";
                  type empty;
                  description
                    "Disable MAC Flush when Port goes Down";
                }
                leaf bd-mac-withdraw {
                  xr:xr-xml-map "l2vpn_cfg:BD_MACWithdraw";
                  xr:xr-cli-map "withdraw disable ";
                  type empty;
                  description "Disable Mac Withdraw";
                }
                leaf bd-mac-withdraw-behavior {
                  xr:xr-xml-map "l2vpn_cfg:BD_MACWithdrawBehavior";
                  xr:xr-cli-map "withdraw state-down ";
                  type Mac-withdraw-behavior;
                  description
                    "MAC withdraw sent on bridge port down";
                }
                leaf bd-mac-learn {
                  xr:xr-xml-map "l2vpn_cfg:BD_MACLearn";
                  xr:xr-cli-map "learning [disable] ";
                  type Mac-learn;
                  description "Enable Mac Learning";
                }
              }

              container nv-satellite {
                xr:xr-xml-map "l2vpn_cfg:nVSatellite";
                description "nV Satellite";
                leaf offload-ipv4-multicast-enable {
                  xr:xr-xml-map "l2vpn_cfg:OffloadIPv4MulticastEnab"+
                    "le";
                  xr:xr-cli-map "l2vpn bridge group <string> bridge"+
                    "-domain <string> nv satellite offload ipv4 mul"+
                    "ticast enable ";
                  type empty;
                  description
                    "Enable IPv4 Multicast Offload to Satellite
                    Nodes";
                }
                leaf enable {
                  xr:xr-xml-map "l2vpn_cfg:Enable";
                  type empty;
                  description "Enable nV Satellite Settings";
                }
              }

              container bridge-domain-pbb {
                xr:xr-xml-map "l2vpn_cfg:BridgeDomainPBB";
                description "Bridge Domain PBB";

                container pbb-edges {
                  xr:xr-xml-map "l2vpn_cfg:PBBEdgeTable";
                  description "PBB Edge";

                  list pbb-edge {
                    xr:xr-xml-map "l2vpn_cfg:PBBEdge";
                    key "isid core-bd-name";
                    description
                      "Configure BD as PBB Edge with ISID and
                      associated PBB Core BD";

                    container pbb-static-mac-mappings {
                      xr:xr-xml-map "l2vpn_cfg:PBBStaticMACMappingT"+
                        "able";
                      description
                        "PBB Static Mac Address Mapping Table";

                      list pbb-static-mac-mapping {
                        xr:xr-xml-map "l2vpn_cfg:PBBStaticMACMappin"+
                          "g";
                        key "address";
                        description
                          "PBB Static Mac Address Mapping
                          Configuration";
                        leaf address {
                          xr:xr-xml-map "l2vpn_cfg:Address";
                          type yang:mac-address;
                          description "Static MAC address";
                        }
                        leaf bmac {
                          xr:xr-xml-map "l2vpn_cfg:BMAC";
                          type yang:mac-address;
                          mandatory true;
                          description "Backbone MAC address";
                        }
                      }
                    }

                    container pbb-edge-dhcp-profile {
                      xr:xr-xml-map "l2vpn_cfg:PBBEdgeDHCPProfile";
                      description "Attach a DHCP profile";
                      leaf profile-id {
                        xr:xr-xml-map "l2vpn_cfg:ProfileId";
                        type Interface-profile;
                        description "Set the snooping profile";
                      }
                      leaf dhcp-snooping-id {
                        xr:xr-xml-map "l2vpn_cfg:DhcpSnoopingID";
                        type string;
                        description "Disable DHCP snooping";
                      }
                    }

                    container pbb-edge-mac {
                      xr:xr-xml-map "l2vpn_cfg:PBBEdgeMAC";
                      description "MAC configuration commands";

                      container pbb-edge-mac-limit {
                        xr:xr-xml-map "l2vpn_cfg:PBBEdgeMACLimit";
                        description
                          "MAC-Limit configuration commands";
                        leaf pbb-edge-mac-limit-action {
                          xr:xr-xml-map "l2vpn_cfg:PBBEdgeMACLimitA"+
                            "ction";
                          xr:xr-cli-map "action (flood)|(no-flood)|"+
                            "(shutdown)|(none) ";
                          type Mac-limit-action;
                          description
                            "MAC address limit enforcement action";
                        }
                        leaf pbb-edge-mac-limit-max {
                          xr:xr-xml-map "l2vpn_cfg:PBBEdgeMACLimitM"+
                            "ax";
                          xr:xr-cli-map "maximum <number> ";
                          type Mac-limit-range;
                          description
                            "Number of MAC addresses after which
                            MAC limit action is taken";
                        }
                        leaf pbb-edge-mac-limit-notif {
                          xr:xr-xml-map "l2vpn_cfg:PBBEdgeMACLimitN"+
                            "otif";
                          xr:xr-cli-map "notification (trap)|(both)"+
                            "|(none)|(syslog) ";
                          type Mac-notification;
                          description
                            "MAC address limit notification action";
                        }
                      }

                      container pbb-edge-mac-aging {
                        xr:xr-xml-map "l2vpn_cfg:PBBEdgeMACAging";
                        description
                          "MAC-Aging configuration commands";
                        leaf pbb-edge-mac-aging-type {
                          xr:xr-xml-map "l2vpn_cfg:PBBEdgeMACAgingT"+
                            "ype";
                          xr:xr-cli-map "aging type (absolute)|(ina"+
                            "ctivity) ";
                          type Mac-aging;
                          description "MAC address aging type";
                        }
                        leaf pbb-edge-mac-aging-time {
                          xr:xr-xml-map "l2vpn_cfg:PBBEdgeMACAgingT"+
                            "ime";
                          xr:xr-cli-map "aging time <number> ";
                          type Mac-aging-range;
                          description "Mac Aging Time";
                        }
                      }

                      container pbb-edge-mac-secure {
                        xr:xr-xml-map "l2vpn_cfg:PBBEdgeMACSecure";
                        description "MAC Secure";
                        leaf logging {
                          xr:xr-xml-map "l2vpn_cfg:Logging";
                          xr:xr-cli-map "logging (disable) ";
                          type L2vpn-logging;
                          description "MAC Secure Logging";
                        }
                        leaf disable {
                          xr:xr-xml-map "l2vpn_cfg:Disable";
                          xr:xr-cli-map "disable ";
                          type empty;
                          description
                            "Disable Virtual instance port MAC
                            Secure";
                        }
                        leaf action {
                          xr:xr-xml-map "l2vpn_cfg:Action";
                          xr:xr-cli-map "action (none)|(shutdown)|("+
                            "restrict) ";
                          type Mac-secure-action;
                          description
                            "MAC secure enforcement action";
                        }
                        leaf enable {
                          xr:xr-xml-map "l2vpn_cfg:Enable";
                          type empty;
                          description "Enable MAC Secure";
                        }
                        leaf accept-shutdown {
                          xr:xr-xml-map "l2vpn_cfg:AcceptShutdown";
                          xr:xr-cli-map "accept-shutdown ";
                          type empty;
                          description
                            "Accept Virtual instance port to be
                            shutdown on mac violation";
                        }
                      }
                      leaf pbb-edge-mac-learning {
                        xr:xr-xml-map "l2vpn_cfg:PBBEdgeMACLearning";
                        xr:xr-cli-map "learning (disable) ";
                        type Mac-learn;
                        description "Enable Mac Learning";
                      }
                    }
                    leaf pbb-edge-igmp-profile {
                      xr:xr-xml-map "l2vpn_cfg:PBBEdgeIGMPProfile";
                      xr:xr-cli-map "igmp snooping profile <string>"+
                        " ";
                      type xr:Cisco-ios-xr-string {
                        length "0..32";
                      }
                      description "Attach a IGMP Snooping profile";
                    }
                    leaf unknown-unicast-bmac {
                      xr:xr-xml-map "l2vpn_cfg:UnknownUnicastBMAC";
                      type yang:mac-address;
                      description
                        "Configure Unknown Unicast BMAC address
                        for PBB Edge Port";
                    }
                    leaf isid {
                      xr:xr-xml-map "l2vpn_cfg:ISID";
                      type Pbbisid-range;
                      description "ISID";
                    }
                    leaf core-bd-name {
                      xr:xr-xml-map "l2vpn_cfg:CoreBDName";
                      type xr:Cisco-ios-xr-string {
                        length "0..27";
                      }
                      description "Core BD Name";
                    }
                  }
                }

                container pbb-core {
                  xr:xr-xml-map "l2vpn_cfg:PBBCore";
                  description "PBB Core";

                  container pbb-core-mac {
                    xr:xr-xml-map "l2vpn_cfg:PBBCoreMAC";
                    description "MAC configuration commands";

                    container pbb-core-mac-aging {
                      xr:xr-xml-map "l2vpn_cfg:PBBCoreMACAging";
                      description
                        "MAC-Aging configuration commands";
                      leaf pbb-core-mac-aging-type {
                        xr:xr-xml-map "l2vpn_cfg:PBBCoreMACAgingTyp"+
                          "e";
                        xr:xr-cli-map "aging type (absolute)|(inact"+
                          "ivity) ";
                        type Mac-aging;
                        description "MAC address aging type";
                      }
                      leaf pbb-core-mac-aging-time {
                        xr:xr-xml-map "l2vpn_cfg:PBBCoreMACAgingTim"+
                          "e";
                        xr:xr-cli-map "aging time <number> ";
                        type Mac-aging-range;
                        description "Mac Aging Time";
                      }
                    }

                    container pbb-core-mac-limit {
                      xr:xr-xml-map "l2vpn_cfg:PBBCoreMACLimit";
                      description
                        "MAC-Limit configuration commands";
                      leaf pbb-core-mac-limit-max {
                        xr:xr-xml-map "l2vpn_cfg:PBBCoreMACLimitMax";
                        xr:xr-cli-map "maximum <number> ";
                        type Mac-limit-range;
                        description
                          "Number of MAC addresses after which MAC
                          limit action is taken";
                      }
                      leaf pbb-core-mac-limit-notif {
                        xr:xr-xml-map "l2vpn_cfg:PBBCoreMACLimitNot"+
                          "if";
                        xr:xr-cli-map "notification (trap)|(both)|("+
                          "none)|(syslog) ";
                        type Mac-notification;
                        description
                          "MAC address limit notification action";
                      }
                      leaf pbb-core-mac-limit-action {
                        xr:xr-xml-map "l2vpn_cfg:PBBCoreMACLimitAct"+
                          "ion";
                        xr:xr-cli-map "action (flood)|(no-flood)|(s"+
                          "hutdown)|(none) ";
                        type Mac-limit-action;
                        description
                          "MAC address limit enforcement action";
                      }
                    }
                    leaf pbb-core-mac-learning {
                      xr:xr-xml-map "l2vpn_cfg:PBBCoreMACLearning";
                      xr:xr-cli-map "learning (disable) ";
                      type Mac-learn;
                      description "Enable Mac Learning";
                    }
                  }

                  container pbb-core-dhcp-profile {
                    xr:xr-xml-map "l2vpn_cfg:PBBCoreDHCPProfile";
                    description "Attach a DHCP profile";
                    leaf profile-id {
                      xr:xr-xml-map "l2vpn_cfg:ProfileId";
                      type Interface-profile;
                      description "Set the snooping profile";
                    }
                    leaf dhcp-snooping-id {
                      xr:xr-xml-map "l2vpn_cfg:DhcpSnoopingID";
                      type string;
                      description "Disable DHCP snooping";
                    }
                  }
                  leaf pbb-core-mmrp-flood-optimization {
                    xr:xr-xml-map "l2vpn_cfg:PBBCoreMMRPFloodOptimi"+
                      "zation";
                    xr:xr-cli-map "l2vpn bridge group <string> brid"+
                      "ge-domain <string> pbb core mmrp-flood-optim"+
                      "ization ";
                    type empty;
                    description
                      "Enabling MMRP PBB-VPLS Flood Optimization";
                  }
                  leaf vlan-id {
                    xr:xr-xml-map "l2vpn_cfg:VLAN_ID";
                    xr:xr-cli-map "l2vpn bridge group <string> brid"+
                      "ge-domain <string> pbb core rewrite ingress "+
                      "tag push dot1ad <number> symmetric ";
                    type Pbbvid-range;
                    description "VLAN ID to push";
                  }
                  leaf pbb-core-igmp-profile {
                    xr:xr-xml-map "l2vpn_cfg:PBBCoreIGMPProfile";
                    type xr:Cisco-ios-xr-string {
                      length "0..32";
                    }
                    description "Attach a IGMP Snooping profile";
                  }
                  leaf enable {
                    xr:xr-xml-map "l2vpn_cfg:Enable";
                    type empty;
                    description
                      "Enable Bridge Domain PBB Core
                      Configuration";
                  }
                  leaf evpn-attribute {
                    xr:xr-xml-map "l2vpn_cfg:EVPNAttribute";
                    xr:xr-cli-map "l2vpn bridge group <string> brid"+
                      "ge-domain <string> pbb core evpn evi <number"+
                      "> ";
                    type Evpnvpnid-range;
                    description "Configure EVPN EVI";
                  }
                }
              }

              container bd-pseudowires {
                xr:xr-xml-map "l2vpn_cfg:BDPseudowireTable";
                description "List of pseudowires";

                list bd-pseudowire {
                  xr:xr-xml-map "l2vpn_cfg:BDPseudowire";
                  key "neighbor pseudowire-id";
                  description "Pseudowire configuration";

                  container pseudowire-dai {
                    xr:xr-xml-map "l2vpn_cfg:PseudowireDAI";
                    description
                      "Access Pseudowire Dynamic ARP Inspection";

                    container pseudowire-dai-address-validation {
                      xr:xr-xml-map "l2vpn_cfg:PseudowireDAIAddress"+
                        "Validation";
                      description "Address Validation";
                      leaf ipv4-verification {
                        xr:xr-xml-map "l2vpn_cfg:IPv4Verification";
                        type L2vpn-verification;
                        description "IPv4 Verification";
                      }
                      leaf destination-mac-verification {
                        xr:xr-xml-map "l2vpn_cfg:DestinationMACVeri"+
                          "fication";
                        type L2vpn-verification;
                        description "Destination MAC Verification";
                      }
                      leaf source-mac-verification {
                        xr:xr-xml-map "l2vpn_cfg:SourceMACVerificat"+
                          "ion";
                        type L2vpn-verification;
                        description "Source MAC Verification";
                      }
                    }
                    leaf logging {
                      xr:xr-xml-map "l2vpn_cfg:Logging";
                      type L2vpn-logging;
                      description "Logging Type";
                    }
                    leaf disable {
                      xr:xr-xml-map "l2vpn_cfg:Disable";
                      type empty;
                      description "Disable Dynamic ARP Inspection";
                    }
                    leaf enable {
                      xr:xr-xml-map "l2vpn_cfg:Enable";
                      type empty;
                      description
                        "Enable Access Pseudowire Dynamic ARP
                        Inspection";
                    }
                  }

                  container bdpw-storm-control-types {
                    xr:xr-xml-map "l2vpn_cfg:BDPWStormControlTable";
                    description "Storm Control";

                    list bdpw-storm-control-type {
                      xr:xr-xml-map "l2vpn_cfg:BDPWStormControlType";
                      key "sctype";
                      description "Storm Control Type";
                      leaf sctype {
                        xr:xr-xml-map "l2vpn_cfg:SCType";
                        type Storm-control;
                        description "Storm Control Type";
                      }
                      uses STORM-CONTROL-UNIT;
                    }
                  }

                  container pseudowire-profile {
                    xr:xr-xml-map "l2vpn_cfg:PseudowireProfile";
                    description "Attach a DHCP profile";
                    leaf profile-id {
                      xr:xr-xml-map "l2vpn_cfg:ProfileId";
                      type Interface-profile;
                      description "Set the snooping profile";
                    }
                    leaf dhcp-snooping-id {
                      xr:xr-xml-map "l2vpn_cfg:DhcpSnoopingID";
                      type string;
                      description "Disable DHCP snooping";
                    }
                  }

                  container bd-pw-static-mac-addresses {
                    xr:xr-xml-map "l2vpn_cfg:BD_PWStaticMACAddressT"+
                      "able";
                    description "Static Mac Address Table";

                    list bd-pw-static-mac-address {
                      xr:xr-xml-map "l2vpn_cfg:BD_PWStaticMacAddres"+
                        "s";
                      key "address";
                      description
                        "Static Mac Address Configuration";
                      leaf address {
                        xr:xr-xml-map "l2vpn_cfg:Address";
                        type yang:mac-address;
                        description "Static MAC address";
                      }
                    }
                  }

                  container pseudowire-ip-source-guard {
                    xr:xr-xml-map "l2vpn_cfg:PseudowireIPSourceGuar"+
                      "d";
                    description "IP Source Guard";
                    leaf logging {
                      xr:xr-xml-map "l2vpn_cfg:Logging";
                      type L2vpn-logging;
                      description "Logging Type";
                    }
                    leaf disable {
                      xr:xr-xml-map "l2vpn_cfg:Disable";
                      type empty;
                      description "Disable Dynamic IP source guard";
                    }
                    leaf enable {
                      xr:xr-xml-map "l2vpn_cfg:Enable";
                      type empty;
                      description "Enable IP Source Guard";
                    }
                  }

                  container pseudowire-mac {
                    xr:xr-xml-map "l2vpn_cfg:PseudowireMAC";
                    description
                      "Bridge-domain Pseudowire MAC
                      configuration commands";

                    container pseudowire-mac-secure {
                      xr:xr-xml-map "l2vpn_cfg:PseudowireMACSecure";
                      description "MAC Secure";
                      leaf logging {
                        xr:xr-xml-map "l2vpn_cfg:Logging";
                        xr:xr-cli-map "logging (disable) ";
                        type L2vpn-logging;
                        description "MAC Secure Logging";
                      }
                      leaf disable {
                        xr:xr-xml-map "l2vpn_cfg:Disable";
                        xr:xr-cli-map "disable ";
                        type empty;
                        description
                          "Disable L2 Pseudowire MAC Secure";
                      }
                      leaf action {
                        xr:xr-xml-map "l2vpn_cfg:Action";
                        xr:xr-cli-map "action (none)|(shutdown)|(re"+
                          "strict) ";
                        type Mac-secure-action;
                        description "MAC secure enforcement action";
                      }
                      leaf enable {
                        xr:xr-xml-map "l2vpn_cfg:Enable";
                        type empty;
                        description "Enable MAC Secure";
                      }
                    }

                    container pseudowire-mac-aging {
                      xr:xr-xml-map "l2vpn_cfg:PseudowireMACAging";
                      description
                        "MAC-Aging configuration commands";
                      leaf pseudowire-mac-aging-type {
                        xr:xr-xml-map "l2vpn_cfg:PseudowireMACAging"+
                          "Type";
                        xr:xr-cli-map "aging type (absolute)|(inact"+
                          "ivity) ";
                        type Mac-aging;
                        description "MAC address aging type";
                      }
                      leaf pseudowire-mac-aging-time {
                        xr:xr-xml-map "l2vpn_cfg:PseudowireMACAging"+
                          "Time";
                        xr:xr-cli-map "aging time <number> ";
                        type Mac-aging-range;
                        description "MAC Aging Time";
                      }
                    }

                    container pseudowire-mac-limit {
                      xr:xr-xml-map "l2vpn_cfg:PseudowireMACLimit";
                      description
                        "MAC-Limit configuration commands";
                      leaf pseudowire-mac-limit-action {
                        xr:xr-xml-map "l2vpn_cfg:PseudowireMACLimit"+
                          "Action";
                        xr:xr-cli-map "action (flood)|(no-flood)|(s"+
                          "hutdown)|(none) ";
                        type Mac-limit-action;
                        description
                          "Bridge Access Pseudowire MAC address
                          limit enforcement action";
                      }
                      leaf pseudowire-mac-limit-notif {
                        xr:xr-xml-map "l2vpn_cfg:PseudowireMACLimit"+
                          "Notif";
                        xr:xr-cli-map "notification (trap)|(both)|("+
                          "none)|(syslog) ";
                        type Mac-notification;
                        description
                          "MAC address limit notification action
                          in a Bridge Access Pseudowire";
                      }
                      leaf pseudowire-mac-limit-max {
                        xr:xr-xml-map "l2vpn_cfg:PseudowireMACLimit"+
                          "Max";
                        xr:xr-cli-map "maximum <number> ";
                        type Mac-limit-range;
                        description
                          "Number of MAC addresses on a Bridge
                          Access Pseudowire after which MAC limit
                          action is taken";
                      }
                    }
                    leaf pseudowire-mac-port-down-flush {
                      xr:xr-xml-map "l2vpn_cfg:PseudowireMACPortDow"+
                        "nFlush";
                      xr:xr-cli-map "port-down flush (disable) ";
                      type Port-down-flush;
                      description
                        "Enable/Disable MAC Flush When Port goes
                        down";
                    }
                    leaf enable {
                      xr:xr-xml-map "l2vpn_cfg:Enable";
                      type empty;
                      description
                        "Bridge-domain Pseudowire MAC
                        configuration mode";
                    }
                    leaf pseudowire-mac-learning {
                      xr:xr-xml-map "l2vpn_cfg:PseudowireMACLearnin"+
                        "g";
                      xr:xr-cli-map "learning (disable) ";
                      type Mac-learn;
                      description "Enable MAC Learning";
                    }
                  }

                  container bd-pw-split-horizon {
                    xr:xr-xml-map "l2vpn_cfg:BD_PWSplitHorizon";
                    description "Split Horizon";

                    container bd-pw-split-horizon-group {
                      xr:xr-xml-map "l2vpn_cfg:BD_PWSplitHorizonGro"+
                        "up";
                      description "Split Horizon Group";
                      leaf enable {
                        xr:xr-xml-map "l2vpn_cfg:Enable";
                        xr:xr-cli-map "split-horizon group ";
                        type empty;
                        description "Enable split horizon group";
                      }
                    }
                  }

                  container bd-pw-mpls-static-labels {
                    xr:xr-xml-map "l2vpn_cfg:BD_PW_MPLSStaticLabels";
                    description "MPLS static labels";
                    leaf local-static-label {
                      xr:xr-xml-map "l2vpn_cfg:LocalStaticLabel";
                      type Pseudowire-label-range;
                      description "Pseudowire local static label";
                    }
                    leaf remote-static-label {
                      xr:xr-xml-map "l2vpn_cfg:RemoteStaticLabel";
                      type Pseudowire-label-range;
                      description "Pseudowire remote static label";
                    }
                  }

                  container bridge-domain-backup-pseudowires {
                    xr:xr-xml-map "l2vpn_cfg:BridgeDomainBackupPseu"+
                      "dowireTable";
                    description "List of pseudowires";

                    list bridge-domain-backup-pseudowire {
                      xr:xr-xml-map "l2vpn_cfg:BridgeDomainBackupPs"+
                        "eudowire";
                      key "neighbor pseudowire-id";
                      description "Backup pseudowire configuration";
                      leaf bridge-domain-backup-pw-class {
                        xr:xr-xml-map "l2vpn_cfg:BridgeDomainBackup"+
                          "PWClass";
                        xr:xr-cli-map "backup neighbor <IPv4 addres"+
                          "s> pw-id <number> pw-class <string> ";
                        type xr:Cisco-ios-xr-string {
                          length "0..32";
                        }
                        description
                          "PW class template name to use for this
                          pseudowire";
                      }
                      leaf neighbor {
                        xr:xr-xml-map "l2vpn_cfg:Neighbor";
                        type inet:ipv4-address-no-zone;
                        description "Neighbor IP address";
                      }
                      leaf pseudowire-id {
                        xr:xr-xml-map "l2vpn_cfg:PseudowireID";
                        type Pseudowire-id-range;
                        description "Pseudowire ID";
                      }
                    }
                  }
                  leaf pseudowire-mld-snoop {
                    xr:xr-xml-map "l2vpn_cfg:PseudowireMLDSnoop";
                    xr:xr-cli-map "mld snooping profile <string> ";
                    type xr:Cisco-ios-xr-string {
                      length "0..32";
                    }
                    description "Attach a MLD Snooping profile";
                  }
                  leaf pseudowire-igmp-snoop {
                    xr:xr-xml-map "l2vpn_cfg:PseudowireIGMPSnoop";
                    xr:xr-cli-map "igmp snooping profile <string> ";
                    type xr:Cisco-ios-xr-string {
                      length "0..32";
                    }
                    description "Attach a IGMP Snooping profile";
                  }
                  leaf pseudowire-flooding {
                    xr:xr-xml-map "l2vpn_cfg:PseudowireFlooding";
                    xr:xr-cli-map "flooding (disable) ";
                    type Interface-traffic-flood;
                    description "Bridge-domain Pseudowire flooding";
                  }
                  leaf bd-pw-class {
                    xr:xr-xml-map "l2vpn_cfg:BD_PWClass";
                    xr:xr-cli-map "pw-class <string> ";
                    type xr:Cisco-ios-xr-string {
                      length "0..32";
                    }
                    description
                      "PW class template name to use for this
                      pseudowire";
                  }
                  leaf pseudowire-flooding-unknown-unicast {
                    xr:xr-xml-map "l2vpn_cfg:PseudowireFloodingUnkn"+
                      "ownUnicast";
                    xr:xr-cli-map "flooding unknown-unicast (disabl"+
                      "e) ";
                    type Interface-traffic-flood;
                    description
                      "Bridge-domain Pseudowire flooding Unknown
                      Unicast";
                  }
                  leaf neighbor {
                    xr:xr-xml-map "l2vpn_cfg:Neighbor";
                    type inet:ipv4-address-no-zone;
                    description "Neighbor IP address";
                  }
                  leaf pseudowire-id {
                    xr:xr-xml-map "l2vpn_cfg:PseudowireID";
                    type Pseudowire-id-range;
                    description "Pseudowire ID";
                  }
                }
              }

              container vfis {
                xr:xr-xml-map "l2vpn_cfg:VFITable";
                description
                  "Specify the virtual forwarding interface
                  name";

                list vfi {
                  xr:xr-xml-map "l2vpn_cfg:VFI";
                  key "name";
                  description
                    "Name of the Virtual Forwarding Interface";

                  container multicast-p2mp {
                    xr:xr-xml-map "l2vpn_cfg:MulticastP2MP";
                    description "Enable Multicast P2MP in this VFI";

                    container transports {
                      xr:xr-xml-map "l2vpn_cfg:TransportTable";
                      description "Multicast P2MP Transport";

                      list transport {
                        xr:xr-xml-map "l2vpn_cfg:Transport";
                        key "transport-name";
                        description "Multicast P2MP Transport Type";
                        leaf attribute-set-name {
                          xr:xr-xml-map "l2vpn_cfg:AttributeSetName";
                          type xr:Cisco-ios-xr-string {
                            length "0..64";
                          }
                          description
                            "Multicast P2MP TE Attribute Set Name";
                        }
                        leaf transport-name {
                          xr:xr-xml-map "l2vpn_cfg:TransportName";
                          type Multicast-p2mp-transport;
                          description "Transport Type";
                        }
                      }
                    }

                    container signalings {
                      xr:xr-xml-map "l2vpn_cfg:SignalingTable";
                      description "Multicast P2MP Signaling Type";

                      list signaling {
                        xr:xr-xml-map "l2vpn_cfg:Signaling";
                        key "signaling-name";
                        description "Multicast P2MP Signaling Type";
                        leaf signaling-name {
                          xr:xr-xml-map "l2vpn_cfg:SignalingName";
                          type Multicast-p2mp-signaling;
                          description "Signaling Type";
                        }
                      }
                    }
                    leaf enable {
                      xr:xr-xml-map "l2vpn_cfg:Enable";
                      type empty;
                      description "Enable Autodiscovery P2MP";
                    }
                  }

                  container vfi-pseudowires {
                    xr:xr-xml-map "l2vpn_cfg:VFIPseudowireTable";
                    description "List of pseudowires";

                    list vfi-pseudowire {
                      xr:xr-xml-map "l2vpn_cfg:VFIPseudowire";
                      key "neighbor pseudowire-id";
                      description "Pseudowire configuration";

                      container vfi-pw-dhcp-snoop {
                        xr:xr-xml-map "l2vpn_cfg:VFI_PW_DHCPSnoop";
                        description
                          "Attach a DHCP Snooping profile";
                        leaf profile-id {
                          xr:xr-xml-map "l2vpn_cfg:ProfileId";
                          type Interface-profile;
                          description "Set the snooping profile";
                        }
                        leaf dhcp-snooping-id {
                          xr:xr-xml-map "l2vpn_cfg:DhcpSnoopingID";
                          type string;
                          description "Disable DHCP snooping";
                        }
                      }

                      container vfi-pw-mpls-static-labels {
                        xr:xr-xml-map "l2vpn_cfg:VFI_PW_MPLSStaticL"+
                          "abels";
                        description "MPLS static labels";
                        leaf local-static-label {
                          xr:xr-xml-map "l2vpn_cfg:LocalStaticLabel";
                          type Pseudowire-label-range;
                          description
                            "Pseudowire local static label";
                        }
                        leaf remote-static-label {
                          xr:xr-xml-map "l2vpn_cfg:RemoteStaticLabe"+
                            "l";
                          type Pseudowire-label-range;
                          description
                            "Pseudowire remote static label";
                        }
                      }

                      container pseudowire-static-mac-addresses {
                        xr:xr-xml-map "l2vpn_cfg:PseudowireStaticMA"+
                          "CAddressTable";
                        description "Static Mac Address Table";

                        list pseudowire-static-mac-address {
                          xr:xr-xml-map "l2vpn_cfg:PseudowireStatic"+
                            "MACAddress";
                          key "address";
                          description
                            "Static Mac Address Configuration";
                          leaf address {
                            xr:xr-xml-map "l2vpn_cfg:Address";
                            type yang:mac-address;
                            description "Static MAC address";
                          }
                        }
                      }
                      leaf vfi-pw-class {
                        xr:xr-xml-map "l2vpn_cfg:VFI_PWClass";
                        xr:xr-cli-map "neighbor <IPv4 address> pw-i"+
                          "d <number> pw-class <string> ";
                        type xr:Cisco-ios-xr-string {
                          length "0..32";
                        }
                        description
                          "PW class template name to use for this
                          pseudowire";
                      }
                      leaf vfi-pw-igmp-snoop {
                        xr:xr-xml-map "l2vpn_cfg:VFI_PW_IGMPSnoop";
                        xr:xr-cli-map "neighbor <IPv4 address> pw-i"+
                          "d <number> igmp snooping profile <string"+
                          "> ";
                        type xr:Cisco-ios-xr-string {
                          length "0..32";
                        }
                        description
                          "Attach a IGMP Snooping profile";
                      }
                      leaf vfi-pw-mld-snoop {
                        xr:xr-xml-map "l2vpn_cfg:VFI_PW_MLDSnoop";
                        xr:xr-cli-map "neighbor <IPv4 address> pw-i"+
                          "d <number> mld snooping profile <string>"+
                          " ";
                        type xr:Cisco-ios-xr-string {
                          length "0..32";
                        }
                        description "Attach a MLD Snooping profile";
                      }
                      leaf neighbor {
                        xr:xr-xml-map "l2vpn_cfg:Neighbor";
                        type inet:ipv4-address-no-zone;
                        description "Neighbor IP address";
                      }
                      leaf pseudowire-id {
                        xr:xr-xml-map "l2vpn_cfg:PseudowireID";
                        type Pseudowire-id-range;
                        description "Pseudowire ID";
                      }
                    }
                  }

                  container bgp-auto-discovery {
                    xr:xr-xml-map "l2vpn_cfg:BGPAutoDiscovery";
                    description
                      "Enable Autodiscovery BGP in this VFI";

                    container ldp-signaling-protocol {
                      xr:xr-xml-map "l2vpn_cfg:LDPSignalingProtocol";
                      description
                        "Signaling Protocol LDP in this VFI
                        configuration";

                      container vplsid {
                        xr:xr-xml-map "l2vpn_cfg:VPLSID";
                        description "VPLS ID";
                        leaf type {
                          xr:xr-xml-map "l2vpn_cfg:Type";
                          type Ldp-vpls-id;
                          description "VPLS-ID Type";
                        }
                        leaf as {
                          xr:xr-xml-map "l2vpn_cfg:AS";
                          when "../type = 'two-byte-as'" {
                            description "../Type = TwoByteAS";
                          }
                          type Vpls-id-as-range;
                          description "Two byte AS number";
                        }
                        leaf as-index {
                          xr:xr-xml-map "l2vpn_cfg:ASIndex";
                          when "../type = 'two-byte-as'" {
                            description "../Type = TwoByteAS";
                          }
                          type Vpls-id-as-index;
                          description "AS index";
                        }
                        leaf address {
                          xr:xr-xml-map "l2vpn_cfg:Address";
                          when "../type = 'ipv4-address'" {
                            description "../Type = IPV4Address";
                          }
                          type inet:ipv4-address-no-zone;
                          description "IPV4 address";
                        }
                        leaf address-index {
                          xr:xr-xml-map "l2vpn_cfg:AddressIndex";
                          when "../type = 'ipv4-address'" {
                            description "../Type = IPV4Address";
                          }
                          type Vpls-id-addr-index;
                          description "Address index";
                        }
                      }

                      container flow-label-load-balance {
                        xr:xr-xml-map "l2vpn_cfg:FlowLabelLoadBalan"+
                          "ce";
                        description
                          "Enable Flow Label based load balancing";
                        leaf flow-label {
                          xr:xr-xml-map "l2vpn_cfg:FlowLabel";
                          type Flow-label-load-balance;
                          description
                            "Flow Label load balance type";
                        }
                        leaf static {
                          xr:xr-xml-map "l2vpn_cfg:Static";
                          type empty;
                          description "Static Flow Label";
                        }
                      }
                      leaf enable {
                        xr:xr-xml-map "l2vpn_cfg:Enable";
                        type empty;
                        description
                          "Enable LDP as Signaling Protocol
                          .Deletion of this object also causes
                          deletion of all objects under
                          LDPSignalingProtocol.";
                      }
                    }

                    container route-distinguisher {
                      xr:xr-xml-map "l2vpn_cfg:RouteDistinguisher";
                      description "Route Distinguisher";
                      leaf type {
                        xr:xr-xml-map "l2vpn_cfg:Type";
                        type Bgp-route-distinguisher;
                        description "Router Distinguisher Type";
                      }
                      leaf as {
                        xr:xr-xml-map "l2vpn_cfg:AS";
                        when "../type = 'two-byte-as' or ../type"+
                          " = 'four-byte-as'" {
                            description
                              "../Type = TwoByteAS or ../Type =
                              FourByteAS";
                        }
                        type Rdas-range;
                        description "Two byte or 4 byte AS number";
                      }
                      leaf as-index {
                        xr:xr-xml-map "l2vpn_cfg:ASIndex";
                        when "../type = 'two-byte-as' or ../type"+
                          " = 'four-byte-as'" {
                            description
                              "../Type = TwoByteAS or ../Type =
                              FourByteAS";
                        }
                        type Rdas-index;
                        description "AS:nn (hex or decimal format)";
                      }
                      leaf address {
                        xr:xr-xml-map "l2vpn_cfg:Address";
                        when "../type = 'ipv4-address'" {
                          description "../Type = IPV4Address";
                        }
                        type inet:ipv4-address-no-zone;
                        description "IPV4 address";
                      }
                      leaf addr-index {
                        xr:xr-xml-map "l2vpn_cfg:AddrIndex";
                        when "../type = 'ipv4-address'" {
                          description "../Type = IPV4Address";
                        }
                        type Rd-addr-index;
                        description "Addr index";
                      }
                    }

                    container bgp-signaling-protocol {
                      xr:xr-xml-map "l2vpn_cfg:BGPSignalingProtocol";
                      description
                        "Enable Signaling Protocol BGP in this
                        VFI";

                      container flow-label-load-balance {
                        xr:xr-xml-map "l2vpn_cfg:FlowLabelLoadBalan"+
                          "ce";
                        description
                          "Enable Flow Label based load balancing";
                        leaf flow-label {
                          xr:xr-xml-map "l2vpn_cfg:FlowLabel";
                          type Flow-label-load-balance;
                          description
                            "Flow Label load balance type";
                        }
                        leaf static {
                          xr:xr-xml-map "l2vpn_cfg:Static";
                          type empty;
                          description "Static Flow Label";
                        }
                      }
                      leaf ve-range {
                        xr:xr-xml-map "l2vpn_cfg:VERange";
                        xr:xr-cli-map "ve-range <number> ";
                        type Vedge-range;
                        description
                          "Local Virtual Edge Block Configurable
                          Range";
                      }
                      leaf veid {
                        xr:xr-xml-map "l2vpn_cfg:VEID";
                        xr:xr-cli-map "ve-id <number> ";
                        type Veid-range;
                        description "Local Virtual Edge Identifier";
                      }
                      leaf enable {
                        xr:xr-xml-map "l2vpn_cfg:Enable";
                        type empty;
                        description
                          "Enable BGP as Signaling Protocol";
                      }
                    }

                    container route-targets {
                      xr:xr-xml-map "l2vpn_cfg:RouteTargetTable";
                      description "Route Target";

                      list route-target {
                        xr:xr-xml-map "l2vpn_cfg:RouteTarget";
                        must "two-byte-as-or-four-byte-as or"+
                          " ipv4-address" {
                          description
                            "TwoByteAS-or-FourbyteAS or IPV4Address
                            must be present.";
                        }
                        key "role format";
                        description "Name of the Route Target";
                        leaf role {
                          xr:xr-xml-map "l2vpn_cfg:Role";
                          type Bgp-route-target-role;
                          description
                            "Role of the router target type";
                        }
                        leaf format {
                          xr:xr-xml-map "l2vpn_cfg:Format";
                          type Bgp-route-target-format;
                          description "Format of the route target";
                        }

                        list two-byte-as-or-four-byte-as {
                          when "../format = 'two-byte-as' or"+
                            " ../format = 'four-byte-as'" {
                              description
                                "../Format = TwoByteAS or ../Format =
                                FourbyteAS";
                          }
                          key "as as-index";
                          description "two byte as or four byte as";
                          leaf as {
                            xr:xr-xml-map "l2vpn_cfg:AS";
                            type Rdas-range;
                            description
                              "Two byte or 4 byte AS number";
                          }
                          leaf as-index {
                            xr:xr-xml-map "l2vpn_cfg:ASIndex";
                            type Rdas-index;
                            description
                              "AS:nn (hex or decimal format)";
                          }
                        }

                        list ipv4-address {
                          when "../format = 'ipv4-address'" {
                            description "../Format = IPV4Address";
                          }
                          key "address addr-index";
                          description "ipv4 address";
                          leaf address {
                            xr:xr-xml-map "l2vpn_cfg:Address";
                            type inet:ipv4-address-no-zone;
                            description "IPV4 address";
                          }
                          leaf addr-index {
                            xr:xr-xml-map "l2vpn_cfg:AddrIndex";
                            type Rd-addr-index;
                            description "Addr index";
                          }
                        }
                      }
                    }
                    leaf ad-control-word {
                      xr:xr-xml-map "l2vpn_cfg:ADControlWord";
                      xr:xr-cli-map "control-word ";
                      type empty;
                      description
                        "Enable control-word for this VFI";
                    }
                    leaf enable {
                      xr:xr-xml-map "l2vpn_cfg:Enable";
                      type empty;
                      description "Enable Autodiscovery BGP";
                    }
                  }
                  leaf vfi-shutdown {
                    xr:xr-xml-map "l2vpn_cfg:VFIShutdown";
                    xr:xr-cli-map "shutdown ";
                    type empty;
                    description "Enabling Shutdown";
                  }
                  leaf vpnid {
                    xr:xr-xml-map "l2vpn_cfg:VPNID";
                    xr:xr-cli-map "vpn-id <number> ";
                    type Vpnid-range;
                    description "VPN Identifier";
                  }
                  leaf name {
                    xr:xr-xml-map "l2vpn_cfg:Name";
                    type xr:Cisco-ios-xr-string {
                      length "0..32";
                    }
                    description
                      "Name of the Virtual Forwarding Interface";
                  }
                }
              }

              container bd-attachment-circuits {
                xr:xr-xml-map "l2vpn_cfg:BDAttachmentCircuitTable";
                description "Attachment Circuit table";

                list bd-attachment-circuit {
                  xr:xr-xml-map "l2vpn_cfg:BDAttachmentCircuit";
                  key "name";
                  description "Name of the Attachment Circuit";

                  container interface-ip-source-guard {
                    xr:xr-xml-map "l2vpn_cfg:InterfaceIPSourceGuard";
                    description "IP Source Guard";
                    leaf logging {
                      xr:xr-xml-map "l2vpn_cfg:Logging";
                      xr:xr-cli-map "logging (disable) ";
                      type L2vpn-logging;
                      description "Logging Type";
                    }
                    leaf disable {
                      xr:xr-xml-map "l2vpn_cfg:Disable";
                      xr:xr-cli-map "disable ";
                      type empty;
                      description
                        "Disable L2 Interface Dynamic IP source
                        guard";
                    }
                    leaf enable {
                      xr:xr-xml-map "l2vpn_cfg:Enable";
                      type empty;
                      description "Enable IP Source Guard";
                    }
                  }

                  container interface-dai {
                    xr:xr-xml-map "l2vpn_cfg:InterfaceDAI";
                    description
                      "L2 Interface Dynamic ARP Inspection";

                    container interface-dai-address-validation {
                      xr:xr-xml-map "l2vpn_cfg:InterfaceDAIAddressV"+
                        "alidation";
                      description "Address Validation";
                      leaf ipv4-verification {
                        xr:xr-xml-map "l2vpn_cfg:IPv4Verification";
                        xr:xr-cli-map "ipv4 (disable) ";
                        type L2vpn-verification;
                        description "IPv4 Verification";
                      }
                      leaf destination-mac-verification {
                        xr:xr-xml-map "l2vpn_cfg:DestinationMACVeri"+
                          "fication";
                        xr:xr-cli-map "dst-mac (disable) ";
                        type L2vpn-verification;
                        description "Destination MAC Verification";
                      }
                      leaf source-mac-verification {
                        xr:xr-xml-map "l2vpn_cfg:SourceMACVerificat"+
                          "ion";
                        xr:xr-cli-map "src-mac (disable) ";
                        type L2vpn-verification;
                        description "Source MAC Verification";
                      }
                      leaf enable {
                        xr:xr-xml-map "l2vpn_cfg:Enable";
                        type empty;
                        description "Enable Address Validation";
                      }
                    }
                    leaf logging {
                      xr:xr-xml-map "l2vpn_cfg:Logging";
                      xr:xr-cli-map "logging (disable) ";
                      type L2vpn-logging;
                      description "Logging Type";
                    }
                    leaf disable {
                      xr:xr-xml-map "l2vpn_cfg:Disable";
                      xr:xr-cli-map "disable ";
                      type empty;
                      description
                        "Disable L2 Interface Dynamic ARP
                        Inspection";
                    }
                    leaf enable {
                      xr:xr-xml-map "l2vpn_cfg:Enable";
                      type empty;
                      description
                        "Enable L2 Interface Dynamic ARP
                        Inspection";
                    }
                  }

                  container interface-profile {
                    xr:xr-xml-map "l2vpn_cfg:InterfaceProfile";
                    description "Attach a DHCP profile";
                    leaf profile-id {
                      xr:xr-xml-map "l2vpn_cfg:ProfileId";
                      type Interface-profile;
                      description "Set the snooping profile";
                    }
                    leaf dhcp-snooping-id {
                      xr:xr-xml-map "l2vpn_cfg:DhcpSnoopingID";
                      type string;
                      description "Disable DHCP snooping";
                    }
                  }

                  container bdac-storm-control-types {
                    xr:xr-xml-map "l2vpn_cfg:BDACStormControlTable";
                    description "Storm Control";

                    list bdac-storm-control-type {
                      xr:xr-xml-map "l2vpn_cfg:BDACStormControlType";
                      key "sctype";
                      description "Storm Control Type";
                      leaf sctype {
                        xr:xr-xml-map "l2vpn_cfg:SCType";
                        type Storm-control;
                        description "Storm Control Type";
                      }
                      uses STORM-CONTROL-UNIT;
                    }
                  }

                  container split-horizon {
                    xr:xr-xml-map "l2vpn_cfg:SplitHorizon";
                    description "Split Horizon";

                    container split-horizon-group-id {
                      xr:xr-xml-map "l2vpn_cfg:SplitHorizonGroupID";
                      description "Split Horizon Group ID";
                      leaf enable {
                        xr:xr-xml-map "l2vpn_cfg:Enable";
                        xr:xr-cli-map "split-horizon group ";
                        type empty;
                        description "Enable split horizon group";
                      }
                    }
                  }

                  container static-mac-addresses {
                    xr:xr-xml-map "l2vpn_cfg:StaticMACAddressTable";
                    description "Static Mac Address Table";

                    list static-mac-address {
                      xr:xr-xml-map "l2vpn_cfg:StaticMACAddress";
                      key "address";
                      description
                        "Static Mac Address Configuration";
                      leaf address {
                        xr:xr-xml-map "l2vpn_cfg:Address";
                        type yang:mac-address;
                        description "Static MAC address";
                      }
                    }
                  }

                  container interface-mac {
                    xr:xr-xml-map "l2vpn_cfg:InterfaceMAC";
                    description "MAC configuration commands";

                    container interface-mac-aging {
                      xr:xr-xml-map "l2vpn_cfg:InterfaceMACAging";
                      description
                        "MAC-Aging configuration commands";
                      leaf interface-mac-aging-time {
                        xr:xr-xml-map "l2vpn_cfg:InterfaceMACAgingT"+
                          "ime";
                        xr:xr-cli-map "aging time <number> ";
                        type Mac-aging-range;
                        description "Mac Aging Time";
                      }
                      leaf interface-mac-aging-type {
                        xr:xr-xml-map "l2vpn_cfg:InterfaceMACAgingT"+
                          "ype";
                        xr:xr-cli-map "aging type (absolute)|(inact"+
                          "ivity) ";
                        type Mac-aging;
                        description "MAC address aging type";
                      }
                    }

                    container interface-mac-secure {
                      xr:xr-xml-map "l2vpn_cfg:InterfaceMACSecure";
                      description "MAC Secure";
                      leaf logging {
                        xr:xr-xml-map "l2vpn_cfg:Logging";
                        xr:xr-cli-map "logging (disable) ";
                        type L2vpn-logging;
                        description "MAC Secure Logging";
                      }
                      leaf disable {
                        xr:xr-xml-map "l2vpn_cfg:Disable";
                        xr:xr-cli-map "disable ";
                        type empty;
                        description
                          "Disable L2 Interface MAC Secure";
                      }
                      leaf action {
                        xr:xr-xml-map "l2vpn_cfg:Action";
                        xr:xr-cli-map "action (none)|(shutdown)|(re"+
                          "strict) ";
                        type Mac-secure-action;
                        description "MAC secure enforcement action";
                      }
                      leaf enable {
                        xr:xr-xml-map "l2vpn_cfg:Enable";
                        type empty;
                        description "Enable MAC Secure";
                      }
                    }

                    container interface-mac-limit {
                      xr:xr-xml-map "l2vpn_cfg:InterfaceMACLimit";
                      description
                        "MAC-Limit configuration commands";
                      leaf interface-mac-limit-max {
                        xr:xr-xml-map "l2vpn_cfg:InterfaceMACLimitM"+
                          "ax";
                        xr:xr-cli-map "maximum <number> ";
                        type Mac-limit-range;
                        description
                          "Number of MAC addresses on an Interface
                          after which MAC limit action is taken";
                      }
                      leaf interface-mac-limit-notif {
                        xr:xr-xml-map "l2vpn_cfg:InterfaceMACLimitN"+
                          "otif";
                        xr:xr-cli-map "notification (trap)|(both)|("+
                          "none)|(syslog) ";
                        type Mac-notification;
                        description
                          "MAC address limit notification action
                          in a Interface";
                      }
                      leaf interface-mac-limit-action {
                        xr:xr-xml-map "l2vpn_cfg:InterfaceMACLimitA"+
                          "ction";
                        xr:xr-cli-map "action (flood)|(no-flood)|(s"+
                          "hutdown)|(none) ";
                        type Mac-limit-action;
                        description
                          "Interface MAC address limit enforcement
                          action";
                      }
                    }
                    leaf interface-mac-port-down-flush {
                      xr:xr-xml-map "l2vpn_cfg:InterfaceMACPortDown"+
                        "Flush";
                      xr:xr-cli-map "port-down flush (disable) ";
                      type Port-down-flush;
                      description
                        "Enable/Disable MAC Flush When Port goes
                        down";
                    }
                    leaf interface-mac-learning {
                      xr:xr-xml-map "l2vpn_cfg:InterfaceMACLearning";
                      xr:xr-cli-map "learning (disable) ";
                      type Mac-learn;
                      description "Enable Mac Learning";
                    }
                  }
                  leaf interface-flooding {
                    xr:xr-xml-map "l2vpn_cfg:InterfaceFlooding";
                    xr:xr-cli-map "flooding (disable) ";
                    type Interface-traffic-flood;
                    description "Enable or Disable Flooding";
                  }
                  leaf interface-igmp-snoop {
                    xr:xr-xml-map "l2vpn_cfg:InterfaceIGMPSnoop";
                    xr:xr-cli-map "igmp snooping profile <string> ";
                    type xr:Cisco-ios-xr-string {
                      length "0..32";
                    }
                    description "Attach a IGMP Snooping profile";
                  }
                  leaf interface-flooding-unknown-unicast {
                    xr:xr-xml-map "l2vpn_cfg:InterfaceFloodingUnkno"+
                      "wnUnicast";
                    xr:xr-cli-map "flooding unknown-unicast (disabl"+
                      "e) ";
                    type Interface-traffic-flood;
                    description
                      "Enable or Disable Unknown Unicast
                      Flooding";
                  }
                  leaf interface-mld-snoop {
                    xr:xr-xml-map "l2vpn_cfg:InterfaceMLDSnoop";
                    xr:xr-cli-map "mld snooping profile <string> ";
                    type xr:Cisco-ios-xr-string {
                      length "0..32";
                    }
                    description "Attach a MLD Snooping profile";
                  }
                  leaf name {
                    xr:xr-xml-map "l2vpn_cfg:Name";
                    type xr:Interface-name;
                    description
                      "The name of the Attachment Circuit";
                  }
                }
              }

              container ip-source-guard {
                xr:xr-xml-map "l2vpn_cfg:IPSourceGuard";
                description "IP Source Guard";
                leaf logging {
                  xr:xr-xml-map "l2vpn_cfg:Logging";
                  xr:xr-cli-map "logging ";
                  type empty;
                  description "Enable Logging";
                }
                leaf enable {
                  xr:xr-xml-map "l2vpn_cfg:Enable";
                  type empty;
                  description "Enable IP Source Guard";
                }
              }

              container dai {
                xr:xr-xml-map "l2vpn_cfg:DAI";
                description "Dynamic ARP Inspection";

                container dai-address-validation {
                  xr:xr-xml-map "l2vpn_cfg:DAIAddressValidation";
                  description "Address Validation";
                  leaf ipv4-verification {
                    xr:xr-xml-map "l2vpn_cfg:IPv4Verification";
                    xr:xr-cli-map "ipv4 ";
                    type empty;
                    description "Enable IPv4 Verification";
                  }
                  leaf destination-mac-verification {
                    xr:xr-xml-map "l2vpn_cfg:DestinationMACVerifica"+
                      "tion";
                    xr:xr-cli-map "dst-mac ";
                    type empty;
                    description
                      "Enable Destination MAC Verification";
                  }
                  leaf source-mac-verification {
                    xr:xr-xml-map "l2vpn_cfg:SourceMACVerification";
                    xr:xr-cli-map "src-mac ";
                    type empty;
                    description "Enable Source MAC Verification";
                  }
                  leaf enable {
                    xr:xr-xml-map "l2vpn_cfg:Enable";
                    type empty;
                    description "Enable Address Validation";
                  }
                }
                leaf logging {
                  xr:xr-xml-map "l2vpn_cfg:Logging";
                  xr:xr-cli-map "logging ";
                  type empty;
                  description "Enable Logging";
                }
                leaf enable {
                  xr:xr-xml-map "l2vpn_cfg:Enable";
                  type empty;
                  description "Enable Dynamic ARP Inspection";
                }
              }

              container routed-interfaces {
                xr:xr-xml-map "l2vpn_cfg:RoutedInterfaceTable";
                description "Bridge Domain Routed Interface Table";

                list routed-interface {
                  xr:xr-xml-map "l2vpn_cfg:RoutedInterface";
                  key "interface-name";
                  description "Bridge Domain Routed Interface";
                  leaf interface-name {
                    xr:xr-xml-map "l2vpn_cfg:InterfaceName";
                    type xr:Interface-name;
                    description "The name of the Routed Interface";
                  }
                }
              }
              leaf coupled-mode {
                xr:xr-xml-map "l2vpn_cfg:CoupledMode";
                xr:xr-cli-map "l2vpn bridge group <string> bridge-d"+
                  "omain <string> coupled-mode ";
                type empty;
                description "Coupled-mode configuration";
              }
              leaf shutdown {
                xr:xr-xml-map "l2vpn_cfg:Shutdown";
                xr:xr-cli-map "l2vpn bridge group <string> bridge-d"+
                  "omain <string> shutdown ";
                type empty;
                description "shutdown the Bridge Domain";
              }
              leaf flooding-unknown-unicast {
                xr:xr-xml-map "l2vpn_cfg:FloodingUnknownUnicast";
                xr:xr-cli-map "l2vpn bridge group <string> bridge-d"+
                  "omain <string> flooding unknown-unicast [disable"+
                  "] ";
                type empty;
                description "Disable Unknown Unicast flooding";
              }
              leaf igmp-snooping-disable {
                xr:xr-xml-map "l2vpn_cfg:IGMPSnoopingDisable";
                xr:xr-cli-map "l2vpn bridge group <string> bridge-d"+
                  "omain <string> igmp snooping disable ";
                type empty;
                description "Disable IGMP Snooping";
              }
              leaf transport-mode {
                xr:xr-xml-map "l2vpn_cfg:TransportMode";
                xr:xr-cli-map "l2vpn bridge group <string> bridge-d"+
                  "omain <string> transport-mode vlan passthrough ";
                type Bridge-domain-transport-mode;
                description "Bridge Domain Transport mode";
              }
              leaf mld-snooping {
                xr:xr-xml-map "l2vpn_cfg:MLDSnooping";
                xr:xr-cli-map "l2vpn bridge group <string> bridge-d"+
                  "omain <string> mld snooping profile <string> ";
                type xr:Cisco-ios-xr-string {
                  length "0..32";
                }
                description "Attach MLD Snooping Profile Name";
              }
              leaf bridge-domain-mtu {
                xr:xr-xml-map "l2vpn_cfg:BridgeDomainMTU";
                xr:xr-cli-map "l2vpn bridge group <string> bridge-d"+
                  "omain <string> mtu <number> ";
                type Bridge-bd-mtu-range;
                units "byte";
                description
                  "Maximum transmission unit for this Bridge
                  Domain";
              }
              leaf dhcp {
                xr:xr-xml-map "l2vpn_cfg:DHCP";
                xr:xr-cli-map "l2vpn bridge group <string> bridge-d"+
                  "omain <string> dhcp ipv4 snoop profile <string> ";
                type string {
                  length "0..32";
                }
                description "DHCPv4 Snooping profile name";
              }
              leaf igmp-snooping {
                xr:xr-xml-map "l2vpn_cfg:IGMPSnooping";
                xr:xr-cli-map "l2vpn bridge group <string> bridge-d"+
                  "omain <string> igmp snooping profile <string> ";
                type xr:Cisco-ios-xr-string {
                  length "0..32";
                }
                description "Attach IGMP Snooping Profile Name";
              }
              leaf flooding {
                xr:xr-xml-map "l2vpn_cfg:Flooding";
                xr:xr-cli-map "l2vpn bridge group <string> bridge-d"+
                  "omain <string> flooding [disable] ";
                type empty;
                description "Disable flooding";
              }
              leaf name {
                xr:xr-xml-map "l2vpn_cfg:Name";
                type xr:Cisco-ios-xr-string {
                  length "0..27";
                }
                description "Name of the bridge domain";
              }
            }
          }
          leaf name {
            xr:xr-xml-map "l2vpn_cfg:Name";
            type xr:Cisco-ios-xr-string {
              length "0..32";
            }
            description "Name of the Bridge group";
          }
        }
      }

      container pseudowire-classes {
        xr:xr-xml-map "l2vpn_cfg:PseudowireClassTable";
        description "List of pseudowire classes";

        list pseudowire-class {
          xr:xr-xml-map "l2vpn_cfg:PseudowireClass";
          key "name";
          description "Pseudowire class";

          container l2tpv3-encapsulation {
            xr:xr-xml-map "l2vpn_cfg:L2TPv3Encapsulation";
            description "L2TPv3 encapsulation";

            container sequencing {
              xr:xr-xml-map "l2vpn_cfg:Sequencing";
              description "Sequencing";
              leaf sequencing {
                xr:xr-xml-map "l2vpn_cfg:Sequencing";
                type L2tpv3-sequencing;
                default "off";
                description "Sequencing";
              }
              leaf resync-threshold {
                xr:xr-xml-map "l2vpn_cfg:ResyncThreshold";
                type Resync-threshold-range;
                default "5";
                description "Out of sequence threshold";
              }
            }

            container type-of-service {
              xr:xr-xml-map "l2vpn_cfg:TypeOfService";
              description "Type of service";
              leaf type-of-service-value {
                xr:xr-xml-map "l2vpn_cfg:TypeOfServiceValue";
                type Type-of-service-range;
                description "Type of service value";
              }
              leaf type-of-service-mode {
                xr:xr-xml-map "l2vpn_cfg:TypeOfServiceMode";
                type Type-of-service-mode;
                description "Type of service mode";
              }
            }

            container signaling-protocol {
              xr:xr-xml-map "l2vpn_cfg:SignalingProtocol";
              description "L2TPv3 signaling protocol";
              leaf protocol {
                xr:xr-xml-map "l2vpn_cfg:Protocol";
                type L2tp-signaling-protocol;
                default "l2tpv3";
                description "L2TPv3 signaling protocol";
              }
              leaf l2tpv3-class-name {
                xr:xr-xml-map "l2vpn_cfg:L2TPv3ClassName";
                type xr:Cisco-ios-xr-string {
                  length "0..32";
                }
                description "Name of the L2TPv3 class name";
              }
            }

            container path-mtu {
              xr:xr-xml-map "l2vpn_cfg:PathMTU";
              description "Path maximum transmission unit";
              leaf enable {
                xr:xr-xml-map "l2vpn_cfg:Enable";
                type empty;
                description "Enable path MTU";
              }
              leaf max-path-mtu {
                xr:xr-xml-map "l2vpn_cfg:MaxPathMTU";
                type Max-path-mtu-range;
                description
                  "Maximum path maximum transmission unit";
              }
            }
            leaf df-bit-set {
              xr:xr-xml-map "l2vpn_cfg:DFBitSet";
              xr:xr-cli-map "dfbit set ";
              type empty;
              description "Set the do not fragment bit to 1";
            }
            leaf cookie-size {
              xr:xr-xml-map "l2vpn_cfg:CookieSize";
              xr:xr-cli-map "cookie size (0)|(4)|(8) ";
              type L2tp-cookie-size;
              default "zero";
              description "Cookie size";
            }
            leaf source-address {
              xr:xr-xml-map "l2vpn_cfg:SourceAddress";
              xr:xr-cli-map "ipv4 source <IPv4 address> ";
              type inet:ipv4-address-no-zone;
              description "Source IP address";
            }
            leaf transport-mode {
              xr:xr-xml-map "l2vpn_cfg:TransportMode";
              xr:xr-cli-map "transport-mode (ethernet)|(vlan) ";
              type Transport-mode;
              description "Transport mode";
            }
            leaf enable {
              xr:xr-xml-map "l2vpn_cfg:Enable";
              type empty;
              description "Enable L2TPv3 encapsulation";
            }
            leaf time-to-live {
              xr:xr-xml-map "l2vpn_cfg:TimeToLive";
              xr:xr-cli-map "ttl <number> ";
              type Time-to-live-range;
              description "Time to live";
            }
          }

          container backup-disable-delay {
            xr:xr-xml-map "l2vpn_cfg:BackupDisableDelay";
            description "Back Up Pseudowire class";
            leaf type {
              xr:xr-xml-map "l2vpn_cfg:Type";
              type Backup-disable;
              description "Delay or Never";
            }
            leaf disable-backup {
              xr:xr-xml-map "l2vpn_cfg:DisableBackup";
              when "../type = 'delay'" {
                description "../Type = Delay";
              }
              type Backup-disable-delay-range;
              description "Disable backup delay";
            }
          }

          container mpls-encapsulation {
            xr:xr-xml-map "l2vpn_cfg:MPLSEncapsulation";
            description "MPLS encapsulation";

            container sequencing {
              xr:xr-xml-map "l2vpn_cfg:Sequencing";
              description "Sequencing";
              leaf sequencing {
                xr:xr-xml-map "l2vpn_cfg:Sequencing";
                type Mpls-sequencing;
                default "off";
                description "Sequencing";
              }
              leaf resync-threshold {
                xr:xr-xml-map "l2vpn_cfg:ResyncThreshold";
                type Resync-threshold-range;
                default "5";
                description "Out of sequence threshold";
              }
            }

            container mpls-redundancy {
              xr:xr-xml-map "l2vpn_cfg:MPLSRedundancy";
              description
                "Redundancy options for MPLS encapsulation";
              leaf redundancy-one-way {
                xr:xr-xml-map "l2vpn_cfg:RedundancyOneWay";
                xr:xr-cli-map "one-way ";
                type empty;
                description
                  "Force one-way PW redundancy behavior in
                  Redundancy Group";
              }
              leaf redundancy-initial-delay {
                xr:xr-xml-map "l2vpn_cfg:RedundancyInitialDelay";
                xr:xr-cli-map "initial-delay <number> ";
                type Pw-redundancy-initial-delay-range;
                units "second";
                description
                  "Initial delay before activating the
                  redundant PW, in seconds";
              }
            }

            container preferred-path {
              xr:xr-xml-map "l2vpn_cfg:PreferredPath";
              description "Preferred path";
              leaf type {
                xr:xr-xml-map "l2vpn_cfg:Type";
                type Preferred-path;
                description "Preferred Path Type";
              }
              leaf interface-tunnel-number {
                xr:xr-xml-map "l2vpn_cfg:InterfaceTunnelNumber";
                type uint32 {
                  range "0..65535";
                }
                description
                  "Interface Tunnel number for preferred path";
              }
              leaf fallback-disable {
                xr:xr-xml-map "l2vpn_cfg:FallbackDisable";
                type empty;
                description "Fallback disable";
              }
            }

            container load-balance-group {
              xr:xr-xml-map "l2vpn_cfg:LoadBalanceGroup";
              description "Load Balancing";

              container flow-label-load-balance {
                xr:xr-xml-map "l2vpn_cfg:FlowLabelLoadBalance";
                description
                  "Enable Flow Label based load balancing";
                leaf flow-label {
                  xr:xr-xml-map "l2vpn_cfg:FlowLabel";
                  type Flow-label-load-balance;
                  description "Flow Label load balance type";
                }
                leaf static {
                  xr:xr-xml-map "l2vpn_cfg:Static";
                  type empty;
                  description "Static Flow Label";
                }
              }
              leaf flow-label-load-balance-code {
                xr:xr-xml-map "l2vpn_cfg:FlowLabelLoadBalanceCode";
                xr:xr-cli-map "flow-label code 17 (disable) ";
                type Flow-label-tlv-code;
                description "Enable Legacy Flow Label TLV code";
              }
              leaf pw-label-load-balance {
                xr:xr-xml-map "l2vpn_cfg:PWLabelLoadBalance";
                xr:xr-cli-map "pw-label ";
                type Load-balance;
                description "Enable PW Label based Load Balancing";
              }
            }
            leaf pw-switching-tlv {
              xr:xr-xml-map "l2vpn_cfg:PWSwitchingTlv";
              xr:xr-cli-map "l2vpn pw-class <string> encapsulation "+
                "mpls switching-tlv hide ";
              type Pw-switching-point-tlv;
              description "Pseudowire Switching Point Tlv";
            }
            leaf static-tag-rewrite {
              xr:xr-xml-map "l2vpn_cfg:StaticTagRewrite";
              xr:xr-cli-map "l2vpn pw-class <string> encapsulation "+
                "mpls tag-rewrite [ingress [vlan <number>]] ";
              type Tag-rewrite-range;
              description "Static Tag rewrite";
            }
            leaf signaling-protocol {
              xr:xr-xml-map "l2vpn_cfg:SignalingProtocol";
              xr:xr-cli-map "l2vpn pw-class <string> encapsulation "+
                "mpls protocol ldp ";
              type Mpls-signaling-protocol;
              default "ldp";
              description "MPLS signaling protocol";
            }
            leaf vccv-type {
              xr:xr-xml-map "l2vpn_cfg:VCCVType";
              xr:xr-cli-map "l2vpn pw-class <string> encapsulation "+
                "mpls vccv verification-type none ";
              type Vccv-verification;
              default "lsp-ping";
              description "VCCV verification type";
            }
            leaf source-address {
              xr:xr-xml-map "l2vpn_cfg:SourceAddress";
              xr:xr-cli-map "l2vpn pw-class <string> encapsulation "+
                "mpls ipv4 source <IPv4 address> ";
              type inet:ipv4-address-no-zone;
              description "Source IP address";
            }
            leaf transport-mode {
              xr:xr-xml-map "l2vpn_cfg:TransportMode";
              xr:xr-cli-map "l2vpn pw-class <string> encapsulation "+
                "mpls transport-mode (ethernet)|(vlan (passthrough)"+
                ") ";
              type Transport-mode;
              description "Transport mode";
            }
            leaf enable {
              xr:xr-xml-map "l2vpn_cfg:Enable";
              type empty;
              description "Enable MPLS encapsulation";
            }
            leaf control-word {
              xr:xr-xml-map "l2vpn_cfg:ControlWord";
              xr:xr-cli-map "l2vpn pw-class <string> encapsulation "+
                "mpls control-word disable ";
              type Control-word;
              description "Enable control word";
            }
          }
          leaf mac-withdraw {
            xr:xr-xml-map "l2vpn_cfg:MACWithdraw";
            xr:xr-cli-map "l2vpn pw-class <string> mac-withdraw ";
            type empty;
            description "Enable backup MAC withdraw";
          }
          leaf enable {
            xr:xr-xml-map "l2vpn_cfg:Enable";
            type empty;
            description "Enable pseudowire class";
          }
          leaf name {
            xr:xr-xml-map "l2vpn_cfg:Name";
            type xr:Cisco-ios-xr-string {
              length "0..32";
            }
            description "Name of the pseudowire class";
          }
        }
      }

      container redundancy {
        xr:xr-xml-map "l2vpn_cfg:Redundancy";
        description "Redundancy groups";

        container iccp-redundancy-groups {
          xr:xr-xml-map "l2vpn_cfg:ICCPGroupTable";
          description
            "List of Inter-Chassis Communication Protocol
            redundancy groups";

          list iccp-redundancy-group {
            xr:xr-xml-map "l2vpn_cfg:ICCPRedundancyGroup";
            key "group-id";
            description "ICCP Redundancy group";

            container iccp-interfaces {
              xr:xr-xml-map "l2vpn_cfg:ICCPInterfaceTable";
              description "List of interfaces";

              list iccp-interface {
                xr:xr-xml-map "l2vpn_cfg:ICCPInterface";
                key "interface-name";
                description "Interface name";
                leaf secondary-vlan-range {
                  xr:xr-xml-map "l2vpn_cfg:SecondaryVLANRange";
                  xr:xr-cli-map "l2vpn redundancy iccp group <numbe"+
                    "r> interface <interface> secondary vlan <strin"+
                    "g> ";
                  type string;
                  description
                    "Secondary VLAN range, in the form of 1-3,5
                    ,8-11";
                }
                leaf recovery-delay {
                  xr:xr-xml-map "l2vpn_cfg:RecoveryDelay";
                  xr:xr-cli-map "l2vpn redundancy iccp group <numbe"+
                    "r> interface <interface> recovery delay <numbe"+
                    "r> ";
                  type uint32 {
                    range "30..3600";
                  }
                  default "180";
                  description "Failure clear recovery delay";
                }
                leaf primary-vlan-range {
                  xr:xr-xml-map "l2vpn_cfg:PrimaryVLANRange";
                  xr:xr-cli-map "l2vpn redundancy iccp group <numbe"+
                    "r> interface <interface> primary vlan <string>"+
                    " ";
                  type string;
                  description
                    "Primary VLAN range, in the form of 1-3,5
                    ,8-11";
                }
                leaf mac-flush-tcn {
                  xr:xr-xml-map "l2vpn_cfg:MACFlushTCN";
                  xr:xr-cli-map "l2vpn redundancy iccp group <numbe"+
                    "r> interface <interface> mac-flush stp-tcn ";
                  type empty;
                  description "Enable STP-TCN MAC flushing";
                }
                leaf interface-name {
                  xr:xr-xml-map "l2vpn_cfg:InterfaceName";
                  type xr:Interface-name;
                  description "Interface name";
                }
              }
            }
            leaf multi-homing-node-id {
              xr:xr-xml-map "l2vpn_cfg:MultiHomingNodeID";
              xr:xr-cli-map "l2vpn redundancy iccp group <number> m"+
                "ulti-homing node-id <number> ";
              type uint32 {
                range "0..254";
              }
              description "ICCP-based service multi-homing node ID";
            }
            leaf group-id {
              xr:xr-xml-map "l2vpn_cfg:GroupID";
              type int32;
              description "Group ID";
            }
          }
        }
        leaf enable {
          xr:xr-xml-map "l2vpn_cfg:Enable";
          type empty;
          description "Enable redundancy groups";
        }
      }
    }

    container pbb {
      xr:xr-xml-map "l2vpn_cfg:PBB";
      description "L2VPN PBB Global";
      leaf backbone-source-mac {
        xr:xr-xml-map "l2vpn_cfg:BackboneSourceMAC";
        type yang:mac-address;
        description "Backbone Source MAC";
      }
    }

    container auto-discovery {
      xr:xr-xml-map "l2vpn_cfg:AutoDiscovery";
      description "Global auto-discovery attributes";

      container bgp-signaling {
        xr:xr-xml-map "l2vpn_cfg:BGPSignaling";
        description "Global bgp signaling attributes";
        leaf mtu-mismatch-ignore {
          xr:xr-xml-map "l2vpn_cfg:MTUMismatchIgnore";
          xr:xr-cli-map "l2vpn autodiscovery bgp signaling-protocol"+
            " bgp mtu mismatch ignore ";
          type empty;
          description
            "Ignore MTU mismatch for auto-discovered
            pseudowires";
        }
      }
    }

    container utility {
      xr:xr-xml-map "l2vpn_cfg:Utility";
      description "L2VPN utilities";

      container logging {
        xr:xr-xml-map "l2vpn_cfg:Logging";
        description "L2VPN logging utility";
        leaf bridge-domain-state-change {
          xr:xr-xml-map "l2vpn_cfg:BridgeDomainStateChange";
          xr:xr-cli-map "l2vpn logging bridge-domain [status] ";
          type empty;
          description "Enable Bridge Domain state change logging";
        }
        leaf pseudowire-state-change {
          xr:xr-xml-map "l2vpn_cfg:PseudowireStateChange";
          xr:xr-cli-map "l2vpn logging pseudowire [status] ";
          type empty;
          description "Enable pseudowire state change logging";
        }
        leaf vfi {
          xr:xr-xml-map "l2vpn_cfg:VFI";
          xr:xr-cli-map "l2vpn logging vfi [status] ";
          type empty;
          description "Enable VFI state change logging";
        }
        leaf nsr-state-change {
          xr:xr-xml-map "l2vpn_cfg:NSRStateChange";
          xr:xr-cli-map "l2vpn logging nsr ";
          type empty;
          description
            "Enable Non Stop Routing state change logging";
        }
        leaf pwhe-replication-state-change {
          xr:xr-xml-map "l2vpn_cfg:PWHEReplicationStateChange";
          xr:xr-cli-map "l2vpn logging pwhe-replication disable ";
          type empty;
          description
            "Enable PW-HE Replication state change logging";
        }
      }
    }

    container snmp {
      xr:xr-xml-map "l2vpn_cfg:SNMP";
      description "SNMP related configuration";

      container mib {
        xr:xr-xml-map "l2vpn_cfg:MIB";
        description "MIB related configuration";

        container mib-interface {
          xr:xr-xml-map "l2vpn_cfg:MIBInterface";
          description "Interface related configuration for MIB";

          container format {
            xr:xr-xml-map "l2vpn_cfg:Format";
            description "MIB interface name output format";
            leaf external-interface-format {
              xr:xr-xml-map "l2vpn_cfg:ExternalInterfaceFormat";
              xr:xr-cli-map "l2vpn snmp mib interface format extern"+
                "al ";
              type empty;
              description
                "Set MIB interface name output in slash
                format (/)";
            }
          }
        }

        container mib-pseudowire {
          xr:xr-xml-map "l2vpn_cfg:MIBPseudowire";
          description "Pseudowire related configuration for MIB";
          leaf statistics {
            xr:xr-xml-map "l2vpn_cfg:Statistics";
            xr:xr-cli-map "l2vpn snmp mib pseudowire statistics ";
            type empty;
            description
              "Enable pseudowire statistics in MIB output";
          }
        }
      }
    }
    leaf nsr {
      xr:xr-xml-map "l2vpn_cfg:NSR";
      xr:xr-cli-map "l2vpn nsr ";
      type empty;
      description "Enable Non-Stop Routing";
    }
    leaf mtu-mismatch-ignore {
      xr:xr-xml-map "l2vpn_cfg:MTUMismatchIgnore";
      xr:xr-cli-map "l2vpn ignore-mtu-mismatch ";
      type empty;
      description "Ignore MTU Mismatch for XCs";
    }
    leaf tcn-propagation {
      xr:xr-xml-map "l2vpn_cfg:TCNPropagation";
      xr:xr-cli-map "l2vpn tcn-propagation ";
      type empty;
      description "Topology change notification propagation";
    }
    leaf pwoam-refresh {
      xr:xr-xml-map "l2vpn_cfg:PWOAMRefresh";
      xr:xr-cli-map "l2vpn pw-oam refresh transmit <number> ";
      type uint32 {
        range "1..4095";
      }
      units "second";
      description "Configure PW OAM refresh interval";
    }
    leaf load-balance {
      xr:xr-xml-map "l2vpn_cfg:LoadBalance";
      xr:xr-cli-map "l2vpn load-balancing [flow (src-dst-mac)|(src-"+
        "dst-ip)] ";
      type Load-balance;
      description "Enable flow load balancing on l2vpn bridges";
    }
    leaf mspw-description {
      xr:xr-xml-map "l2vpn_cfg:MSPWDescription";
      xr:xr-cli-map "l2vpn description <string> ";
      type xr:Cisco-ios-xr-string {
        length "0..64";
      }
      description "MS-PW global description";
    }
    leaf pw-status-disable {
      xr:xr-xml-map "l2vpn_cfg:PWStatusDisable";
      xr:xr-cli-map "l2vpn pw-status disable ";
      type empty;
      description "Disable PW status";
    }
    leaf enable {
      xr:xr-xml-map "l2vpn_cfg:Enable";
      type empty;
      description "Enable L2VPN feature";
    }
    leaf pw-grouping {
      xr:xr-xml-map "l2vpn_cfg:PWGrouping";
      xr:xr-cli-map "l2vpn pw-grouping ";
      type empty;
      description "Enable PW grouping";
    }
    leaf capability {
      xr:xr-xml-map "l2vpn_cfg:Capability";
      xr:xr-cli-map "l2vpn capability (single-mode)|(high-mode) ";
      type L2vpn-capability-mode;
      description "L2VPN Capability Mode";
    }
    leaf l2vpn-router-id {
      xr:xr-xml-map "l2vpn_cfg:L2VPNRouterID";
      xr:xr-cli-map "l2vpn router-id <IPv4 address> ";
      type inet:ipv4-address-no-zone;
      description "Global L2VPN Router ID";
    }
  }

  container generic-interface-lists {
    xr:xr-xml-map "iflist_cfg:GenericInterfaceListTable";
    description "generic interface lists";

    list generic-interface {
      xr:xr-xml-map "iflist_cfg:GenericInterfaceList";
      key "generic-interface-list-name";
      description "Bridge group";

      container interfaces {
        xr:xr-xml-map "iflist_cfg:InterfaceTable";
        description "Interface table";

        list interface {
          xr:xr-xml-map "iflist_cfg:Interface";
          key "interface-name";
          description "Interface";
          leaf enable {
            xr:xr-xml-map "iflist_cfg:Enable";
            xr:xr-cli-map "generic-interface-list <string> interfac"+
              "e (<interface>)|(<interface>) ";
            type empty;
            description "Enable interface";
          }
          leaf interface-name {
            xr:xr-xml-map "iflist_cfg:InterfaceName";
            type xr:Interface-name;
            description "Name of the interface";
          }
        }
      }
      leaf enable {
        xr:xr-xml-map "iflist_cfg:Enable";
        type empty;
        description "Enable interface list";
      }
      leaf generic-interface-list-name {
        xr:xr-xml-map "iflist_cfg:GenericInterfaceListName";
        type xr:Cisco-ios-xr-string {
          length "0..32";
        }
        description "Name of the interface list";
      }
    }
  }

  container evpn {
    xr:xr-xml-map "l2vpn_cfg:EVPN";
    description "evpn";

    container evpn-tables {
      xr:xr-xml-map "l2vpn_cfg:EVPNTables";
      description "EVPN submodes";

      container evpn-timers {
        xr:xr-xml-map "l2vpn_cfg:EVPNTimers";
        description "Enter EVPN timers configuration submode";
        leaf evpn-programming {
          xr:xr-xml-map "l2vpn_cfg:EVPNProgramming";
          type uint32 {
            range "0..100000";
          }
          default "1500";
          description "Global Programming timer";
        }
        leaf evpn-flush-again {
          xr:xr-xml-map "l2vpn_cfg:EVPNFlushAgain";
          type uint32 {
            range "0..120";
          }
          default "60";
          description "Global MAC Flush again timer";
        }
        leaf evpn-recovery {
          xr:xr-xml-map "l2vpn_cfg:EVPNRecovery";
          xr:xr-cli-map "recovery <number> ";
          type uint32 {
            range "20..3600";
          }
          default "30";
          description "Global Recovery timer";
        }
        leaf enable {
          xr:xr-xml-map "l2vpn_cfg:Enable";
          type empty;
          description "Enable EVPN timers";
        }
        leaf evpn-peering {
          xr:xr-xml-map "l2vpn_cfg:EVPNPeering";
          xr:xr-cli-map "peering <number> ";
          type uint32 {
            range "0..300";
          }
          default "3";
          description "Global Peering timer";
        }
      }

      container evpnevis {
        xr:xr-xml-map "l2vpn_cfg:EVPNEVIMode";
        description "Enter EVPN EVI configuration submode";

        list evpnevi {
          xr:xr-xml-map "l2vpn_cfg:EVPNEVI";
          key "eviid";
          description "Enter EVPN EVI configuration submode";

          container evi-load-balancing {
            xr:xr-xml-map "l2vpn_cfg:EVILoadBalancing";
            description
              "Enter EVI Loadbalancing configuration submode";
            leaf evi-flow-label {
              xr:xr-xml-map "l2vpn_cfg:EVIFlowLabel";
              xr:xr-cli-map "flow-label static ";
              type empty;
              description "Enable Flow Label based load balancing";
            }
            leaf enable {
              xr:xr-xml-map "l2vpn_cfg:Enable";
              type empty;
              description "Enable EVI Loadbalancing";
            }
          }

          container evpnevibgp-auto-discovery {
            xr:xr-xml-map "l2vpn_cfg:EVPNEVIBGPAutoDiscovery";
            description "Enable Autodiscovery BGP in EVPN EVI";

            container evpn-route-targets {
              xr:xr-xml-map "l2vpn_cfg:EVPNRouteTargetTable";
              description "Route Target";

              list evpn-route-target {
                xr:xr-xml-map "l2vpn_cfg:EVPNRouteTarget";
                must "two-byte-as-or-four-byte-as or ipv4-address" {
                  description
                    "TwoByteAS-or-FourbyteAS or IPV4Address
                    must be present.";
                }
                key "role format";
                description "Name of the Route Target";
                leaf role {
                  xr:xr-xml-map "l2vpn_cfg:Role";
                  type Bgp-route-target-role;
                  description "Role of the router target type";
                }
                leaf format {
                  xr:xr-xml-map "l2vpn_cfg:Format";
                  type Bgp-route-target-format;
                  description "Format of the route target";
                }

                list two-byte-as-or-four-byte-as {
                  when "../format = 'two-byte-as' or ../format ="+
                    " 'four-byte-as'" {
                      description
                        "../Format = TwoByteAS or ../Format =
                        FourbyteAS";
                  }
                  key "as as-index";
                  description "two byte as or four byte as";
                  leaf as {
                    xr:xr-xml-map "l2vpn_cfg:AS";
                    type Rdas-range;
                    description "Two byte or 4 byte AS number";
                  }
                  leaf as-index {
                    xr:xr-xml-map "l2vpn_cfg:ASIndex";
                    type Rdas-index;
                    description "AS:nn (hex or decimal format)";
                  }
                }

                list ipv4-address {
                  when "../format = 'ipv4-address'" {
                    description "../Format = IPV4Address";
                  }
                  key "address addr-index";
                  description "ipv4 address";
                  leaf address {
                    xr:xr-xml-map "l2vpn_cfg:Address";
                    type inet:ipv4-address-no-zone;
                    description "IPV4 address";
                  }
                  leaf addr-index {
                    xr:xr-xml-map "l2vpn_cfg:AddrIndex";
                    type Rd-addr-index;
                    description "Addr index";
                  }
                }
              }
            }
            leaf enable {
              xr:xr-xml-map "l2vpn_cfg:Enable";
              type empty;
              description "Enable Autodiscovery BGP";
            }
            uses EVPN-ROUTE-DISTINGUISHER;
          }
          leaf eviid {
            xr:xr-xml-map "l2vpn_cfg:EVIID";
            type Vpnid-range;
            description "EVI ID";
          }
        }
      }

      container evpn-load-balancing {
        xr:xr-xml-map "l2vpn_cfg:EVPNLoadBalancing";
        description
          "Enter EVPN Loadbalancing configuration submode";
        leaf evpn-flow-label {
          xr:xr-xml-map "l2vpn_cfg:EVPNFlowLabel";
          xr:xr-cli-map "flow-label static ";
          type empty;
          description "Enable Flow Label based load balancing";
        }
        leaf enable {
          xr:xr-xml-map "l2vpn_cfg:Enable";
          type empty;
          description "Enable EVPN Loadbalancing";
        }
      }

      container evpnbgp-auto-discovery {
        xr:xr-xml-map "l2vpn_cfg:EVPNBGPAutoDiscovery";
        description "Enable Autodiscovery BGP in EVPN";
        leaf enable {
          xr:xr-xml-map "l2vpn_cfg:Enable";
          type empty;
          description "Enable Autodiscovery BGP";
        }
        uses EVPN-ROUTE-DISTINGUISHER;
      }

      container evpn-interfaces {
        xr:xr-xml-map "l2vpn_cfg:EVPNInterfaceTable";
        description "Attachment Circuit interfaces";

        list evpn-interface {
          xr:xr-xml-map "l2vpn_cfg:EVPNInterface";
          key "interface-name";
          description "Attachment circuit interface";

          container evpnac-timers {
            xr:xr-xml-map "l2vpn_cfg:EVPNACTimers";
            description
              "Enter Interface-specific timers configuration
              submode";
            leaf evpnac-flush-again {
              xr:xr-xml-map "l2vpn_cfg:EVPNACFlushAgain";
              type uint32 {
                range "0..120";
              }
              default "60";
              description
                "Interface-specific MAC Flush again timer";
            }
            leaf enable {
              xr:xr-xml-map "l2vpn_cfg:Enable";
              type empty;
              description "Enable Interface-specific timers";
            }
            leaf evpnac-recovery {
              xr:xr-xml-map "l2vpn_cfg:EVPNACRecovery";
              xr:xr-cli-map "recovery <number> ";
              type uint32 {
                range "20..3600";
              }
              default "30";
              description "Interface-specific Recovery timer";
            }
          }

          container ethernet-segment {
            xr:xr-xml-map "l2vpn_cfg:EthernetSegment";
            description
              "Enter Ethernet Segment configuration submode";

            container identifier-type0 {
              xr:xr-xml-map "l2vpn_cfg:IdentifierType0";
              description "Ethernet segment identifier (Type 0)";
              leaf bytes1 {
                xr:xr-xml-map "l2vpn_cfg:Bytes1";
                type xr:Hex-integer;
                description "Type 0's 1st Byte";
              }
              leaf bytes23 {
                xr:xr-xml-map "l2vpn_cfg:Bytes23";
                type xr:Hex-integer;
                units "byte";
                description "Type 0's 2nd and 3rd Bytes";
              }
              leaf bytes45 {
                xr:xr-xml-map "l2vpn_cfg:Bytes45";
                type xr:Hex-integer;
                units "byte";
                description "Type 0's 4th and 5th Bytes";
              }
              leaf bytes67 {
                xr:xr-xml-map "l2vpn_cfg:Bytes67";
                type xr:Hex-integer;
                units "byte";
                description "Type 0's 6th and 7th Bytes";
              }
              leaf bytes89 {
                xr:xr-xml-map "l2vpn_cfg:Bytes89";
                type xr:Hex-integer;
                units "byte";
                description "Type 0's 8th and 9th Bytes";
              }
            }

            container manual-service-carving {
              xr:xr-xml-map "l2vpn_cfg:ManualServiceCarving";
              description
                "Enter Manual service carving configuration
                submode";

              container service-list {
                xr:xr-xml-map "l2vpn_cfg:ServiceList";
                description
                  "Manual service carving primary,secondary
                  lists";
                leaf primary {
                  xr:xr-xml-map "l2vpn_cfg:Primary";
                  type string {
                    length "0..150";
                  }
                  description "Primary services list";
                }
                leaf secondary {
                  xr:xr-xml-map "l2vpn_cfg:Secondary";
                  type string {
                    length "0..150";
                  }
                  description "Secondary services list";
                }
              }
              leaf enable {
                xr:xr-xml-map "l2vpn_cfg:Enable";
                type empty;
                description "Enable Manual service carving";
              }
            }
            leaf force-single-homed {
              xr:xr-xml-map "l2vpn_cfg:ForceSingleHomed";
              xr:xr-cli-map "force single-homed ";
              type empty;
              description
                "Force ethernet segment to remain
                single-homed";
            }
            leaf load-balancing-per-service {
              xr:xr-xml-map "l2vpn_cfg:LoadBalancingPerService";
              xr:xr-cli-map "load-balancing-mode (per-service)|(sin"+
                "gle-active) ";
              type empty;
              description "Enable per service load balancing mode";
            }
            leaf es-import-route-target {
              xr:xr-xml-map "l2vpn_cfg:ESImportRouteTarget";
              type yang:mac-address;
              description "ES-Import Route Target";
            }
            leaf enable {
              xr:xr-xml-map "l2vpn_cfg:Enable";
              type empty;
              description "Enable Ethernet Segment";
            }
            leaf backbone-source-mac {
              xr:xr-xml-map "l2vpn_cfg:BackboneSourceMAC";
              type yang:mac-address;
              description "Backbone Source MAC";
            }
          }
          leaf mac-flush {
            xr:xr-xml-map "l2vpn_cfg:MACFlush";
            xr:xr-cli-map "evpn interface (<interface>)|(<interface"+
              ">) mac-flush mvrp ";
            type empty;
            description "Enable MVRP MAC Flush mode";
          }
          leaf interface-name {
            xr:xr-xml-map "l2vpn_cfg:InterfaceName";
            type xr:Interface-name;
            description "Name of the attachment circuit interface";
          }
        }
      }
    }

    container standard-version {
      xr:xr-xml-map "l2vpn_cfg:StandardVersion";
      description "Set Standard EVPN Version";
      leaf draft-04 {
        xr:xr-xml-map "l2vpn_cfg:Draft-04";
        xr:xr-cli-map "evpn standard-version draft-04 ";
        type empty;
        description "Set IETF Draft version to 04";
      }
    }
    leaf enable {
      xr:xr-xml-map "l2vpn_cfg:Enable";
      type empty;
      description "Enable EVPN feature";
    }
  }

  augment "/a1:interface-configurations/a1:interface-configuration" {

    container pseudowire-ether {
      xr:xr-xml-map "l2vpn_pw_ether_cfg:PseudowireEther";
      description "PW-Ether attributes";
      leaf generic-interface-list {
        xr:xr-xml-map "l2vpn_pw_ether_cfg:GenericInterfaceList";
        type xr:Cisco-ios-xr-string {
          length "0..32";
        }
        description "Name of the interface list";
      }
      leaf l2-overhead {
        xr:xr-xml-map "l2vpn_pw_ether_cfg:L2Overhead";
        type uint32 {
          range "1..64";
        }
        description "PW Ether L2 overhead requirement";
      }
    }
    description
      "This augment extends the configuration data of
      'Cisco-IOS-XR-ifmgr-cfg'";
  }

  augment "/a1:interface-configurations/a1:interface-configuration" {

    container pseudowire-iw {
      xr:xr-xml-map "l2vpn_pw_iw_cfg:PseudowireIW";
      description "PW-IW attributes";
      leaf l2-overhead {
        xr:xr-xml-map "l2vpn_pw_iw_cfg:L2Overhead";
        type uint32 {
          range "1..64";
        }
        units "byte";
        description "L2 overhead size in bytes";
      }
      leaf generic-interface-list {
        xr:xr-xml-map "l2vpn_pw_iw_cfg:GenericInterfaceList";
        type xr:Cisco-ios-xr-string {
          length "0..32";
        }
        description "Name of the interface list";
      }
    }
    description
      "This augment extends the configuration data of
      'Cisco-IOS-XR-ifmgr-cfg'";
  }

  augment "/a1:interface-configurations/a1:interface-configuration" {

    container l2-transport {
      xr:xr-xml-map "l2vpn_ac_l2transport_cfg:L2Transport";
      description
        "Interface Layer 2 Transport service
        configuration data";
      leaf enabled {
        xr:xr-xml-map "l2vpn_ac_l2transport_cfg:Enabled";
        type empty;
        description
          "This object is only valid on physical
          interfaces and it controls whether that
          interface is a port mode Layer 2 attachment
          circuit (note that for subinterfaces, the Layer
          2 property is specified when the subinterface
          is created).The object must be set before any
          other L2Transport configuration is supplied for
          the interface, and must be the last
          per-interface configuration object to be
          removed.";
      }
    }
    description
      "This augment extends the configuration data of
      'Cisco-IOS-XR-ifmgr-cfg'";
  }

  augment "/a2:snmp/a2:notification" {

    container vpls {
      xr:xr-xml-map "vplsmib_cfg:VPLS";
      description
        "CISCO-IETF-VPLS-GENERIC-MIB notification
        configuration";
      leaf full-clear {
        xr:xr-xml-map "vplsmib_cfg:FullClear";
        type empty;
        description "Enable cvplsFwdFullAlarmCleared notification";
      }
      leaf status {
        xr:xr-xml-map "vplsmib_cfg:Status";
        type empty;
        description "Enable cvplsStatusChanged notification";
      }
      leaf enable {
        xr:xr-xml-map "vplsmib_cfg:Enable";
        type empty;
        description
          "Enable CISCO-IETF-VPLS-GENERIC-MIB
          notifications";
      }
      leaf full-raise {
        xr:xr-xml-map "vplsmib_cfg:FullRaise";
        type empty;
        description "Enable cvplsFwdFullAlarmRaised notification";
      }
    }
    description
      "This augment extends the configuration data of
      'Cisco-IOS-XR-snmp-agent-cfg'";
  }

  augment "/a2:snmp/a2:notification" {

    container l2vpn {
      xr:xr-xml-map "pwmib_cfg:L2VPN";
      description "CISCO-IETF-PW-MIB notification configuration";
      leaf cisco {
        xr:xr-xml-map "pwmib_cfg:Cisco";
        type empty;
        description "Enable Cisco format including extra varbinds";
      }
      leaf enable {
        xr:xr-xml-map "pwmib_cfg:Enable";
        type empty;
        description "Enable CISCO-IETF-PW-MIB notifications";
      }
      leaf vc-down {
        xr:xr-xml-map "pwmib_cfg:VCDown";
        type empty;
        description "Enable cpwVcDown notification";
      }
      leaf vc-up {
        xr:xr-xml-map "pwmib_cfg:VCUp";
        type empty;
        description "Enable cpwVcUp notification";
      }
    }
    description
      "This augment extends the configuration data of
      'Cisco-IOS-XR-snmp-agent-cfg'";
  }
}
