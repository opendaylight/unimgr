/*
 * Copyright (c) 2015 Cable Television Laboratories, Inc. All rights reserved.
 *
 * This program and the accompanying materials are made available under the
 * terms of the Eclipse Public License v1.0 which accompanies this distribution,
 * and is available at http://www.eclipse.org/legal/epl-v10.html INTERNAL
 */
module unimgr-cisco-xr-driver-impl {
    yang-version 1;
    namespace "urn:opendaylight:params:xml:ns:yang:unimgr:cisco-xr-driver:impl";
    prefix "unimgr-cisco-xr-driver-impl";

    import config { prefix config; revision-date 2013-04-05; }
    import opendaylight-md-sal-binding { prefix md-sal-binding; revision-date 2013-10-28;}

    description
        "Service definition for unimgr project";

    revision "2016-05-18" {
        description
            "Updated revision.";
    }

    identity unimgr-cisco-xr-driver {
        base config:module-type;
        config:java-name-prefix UnimgrXRDriver;
    }

    augment "/config:modules/config:module/config:configuration" {
        case unimgr-cisco-xr-driver {
            when "/config:modules/config:module/config:type = 'unimgr-cisco-xr-driver'";
            container broker {
                uses config:service-ref {
                    refine type {
                        mandatory true;
                        config:required-identity md-sal-binding:binding-broker-osgi-registry;
                    }
                }
            }
            container data-broker {
                uses config:service-ref {
                    refine type {
                        mandatory false;
                        config:required-identity md-sal-binding:binding-async-data-broker;
                    }
                }
            }
        }
    }
}
