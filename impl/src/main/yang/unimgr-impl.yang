/*
 * Copyright (c) 2015 Cable Television Laboratories, Inc. All rights reserved.
 *
 * This program and the accompanying materials are made available under the
 * terms of the Eclipse Public License v1.0 which accompanies this distribution,
 * and is available at http://www.eclipse.org/legal/epl-v10.html INTERNAL
 */
module unimgr-impl {
    yang-version 1;
    namespace "urn:opendaylight:params:xml:ns:yang:unimgr:impl";
    prefix "unimgr-impl";

    import config { prefix config; revision-date 2013-04-05; }

    description
        "Service definition for unimgr project";

    revision "2016-05-25" {
        description
            "Updated revision.";
    }

    identity unimgr {
        base config:module-type;
        config:java-name-prefix Unimgr;
    }

    augment "/config:modules/config:module/config:configuration" {
        case unimgr {
            when "/config:modules/config:module/config:type = 'unimgr'";
        }
    }
}
