module msea-uni-evc-interface {

	namespace "http://www.microsemi.com/microsemi-edge-assure/msea-uni-evc-interface";
	prefix "msea-if"; //MicroSemi EdgeAssure (msea)

	import ietf-yang-types {
		prefix yang;
		revision-date 2013-07-15;
	}
	
	import msea-types {
		prefix msea;
		revision-date 2016-02-29;
	}
	
	import ietf-interfaces { 
		prefix "if";
	}

	import iana-if-type { 
		prefix "ianaift"; 
	}

	organization
	"Microsemi Inc., FTD Division";

	contact
	"Web URL: http://www.microsemi.com/
	E-mail: info@microsemi.com
	Postal: Microsemi Corporation Corporate Headquarters
	One Enterprise Aliso Viejo,
	CA 92656
	U.S.A.
	Phone: +1 949 380 6100
	Fax: +1 949 215-4996";


	description
	"This YANG module is based on the MEF 40 SNMP model, for the management 
	objects for the management of User Network Interfaces (UNIs). 
	It has been converted to YANG and modified slightly to suit the 
	EdgeAssure SFP which has some extra constraints that are not handled by 
	the original model

	Copyright 2016 Microsemi Inc.
	All rights reserved.";

	reference
	"***************************************************************************
	Reference Overview

	A number of base documents have been used to create this MIB. The following
	are the abbreviations for the baseline documents:
	[MEF 40] refers to SNMP MIB
	[MEF6.1] refers to MEF 6.1 'Ethernet Services Definitions - Phase 2',
	April 2008
	[MEF 6.1.1] refers to MEF 6.1.1 'Layer 2 Control Protocol Handling Amendment
	to MEF 6.1', January 2012
	[MEF 7.2] refers to MEF 7.2 'Carrier Ethernet Management Information Model',
	January 2013
	[MEF 10.2] refers to MEF 10.2 'Ethernet Services Attributes Phase 2',
	October 2009
	[MEF 26.1] refers to MEF 26.1 'External Network Network Interface (ENNI) -
	Phase 2', January 2012
	[Q.840.1] refers to 'ITU-T Requirements and analysis for NMS-EMS
	management interface of Ethernet over Transport and Metro Ethernet
	Network (EoT/MEN)', March 2007
	****************************************************************************";

	revision "2016-03-17" {
		description
		"Initial Version. Sean Condon - Microsemi";
		reference "MEF 6.2";
	}


  typedef MefServiceInterfaceType {
    type bits {
//      bit bUni1d1;
//      bit bUni1d2;
      bit bUni2d1 {description "Only bUni2d1 is supported by EdgeAssure 1000";}
//      bit bUni2d2;
//      bit bEnni;
//      bit bEnniVuni;
    }
    
    default "bUni2d1";
    description     
     "A MEF Interface can be one of several types:
      
      bUni1d1    UNI Type 1.1 See MEF 13. Non-multiplexed UNI for services such as EPL,
      bUni1d2    UNI Type 1.2 See MEF 13. Multiplexed UNI for services such as EVPL, 
      bUni2d1    UNI Type 2.1 See MEF 20 section 7
      bUni2d2    UNI Type 2.2 See MEF 20 section 7
      bEnni      ENNI
      bEnniVuni  VUNI on an ENNI";
    reference       
     "[MEF 6.1] 6.0";
  }

  typedef l2cp-dest-mac-address {
      type string {
          pattern '01-80-[cC]2-(00-){2}[02][0-9a-fA-F]|01:80:[cC]2:(00:){2}[02][0-9a-fA-F]';
      }
      description
         "The L2CP Destination MAC address for CoS 
			Identifier type of 'l2cp' and is ignored for other types.
	
			Valid values are 01-80-C2-00-00-00 through 01-80-C2-00-00-0F and
			01-80-C2-00-00-20 through 01-80-C2-00-00-2F
			
			Values can be upper or lower case and can be separated by hyphen or colon (but not both)";
  }
  

  
	typedef l2cp-destination-address {
		type enumeration {
			enum destinationAddressOnly {
				description "L2CP selection is determined by
				MAC Destination Address only";
			}
		
//						enum daPlusProtocol {
//							description "L2CP selection is determined by
//								MAC Destination Address plus
//								Ethernet protocol";
//						}
//						
//						enum daPlusProtocolPlusSubtype {
//							description "L2CP selection is determined by
//							MAC Destination Address plus
//							Ethernet protocol plus subtype";
//						}
		}		
	}
	
/*** OBJECT DEFINITIONS ***/
  //
  // Augments ietf-interfaces (only of type ethernetCsmacd) with MEF Services
  //
  augment "/if:interfaces/if:interface" {
      when "if:type='ianaift:ethernetCsmacd' and (if:name='eth0' or if:name='eth1')";
      
      leaf frame-format { //aka mefServiceInterfaceCfgFrameFormat
        type enumeration {
          enum noTag    { 
        	  description "Indicates that all data on the interface 
				is regarded as untagged, regardless of it ingress type"; }
          enum ctag     { 
        	  description "Ingress frames with CTAG(vlan>0) will be 
        		  regared as 'VLAN tagged'; with CTAG(vlan=0) as Priority; otherwise untagged";
          }
          enum stag     { 
        	  description "Ingress frames with STAG(vlan>0) will be 
        		  regared as 'VLAN tagged'; with STAG(vlan=0) as Priority; otherwise untagged";
		  }
//          enum stagCtag { description "Indicates that service traffic identified 
//				with both an S-TAG (outer tag) and a C-TAG 
//				(inner tag)"; }
        }
	    //default noTag; --These defaults break the validation - not using them in Eagle
        description 
         "This object indicates the interface frame format type that the
          interface can recognize.";
        reference   
         "[MEF 6.1] 6.0";
      }

      leaf interface-ingress-bwp-group-index { //aka mefServiceInterfaceCfgIngressBwpGrpIndex
        type leafref {
          path "/if:interfaces/msea-if:interface-profiles/msea-if:interface-bwp-group/msea-if:group-index";
        }
        description 
         "This object is the index number of the ingress bandwidth profile group
          associated with the current interface. A value of 0 indicates that no
          interface ingress bandwidth profile group is associated with the 
          interface.
          
          This index indicates the specific bandwidth profile group previously 
          configured via mefServiceBwpGrpCfgTable and mefServiceBwpCfgTable 
          using this value for mefServiceBwpGrpCfgIndex. There may be multiple 
          entries in mefServiceBwpCfgTable using this index, each containing
          bandwidth parameters for a different Class of Service Identifier.";
        reference   
         "[MEF 6.1] 6.0; [MEF 7.2] 6.2.1.2";
      }
      
	  leaf ce-vid-untagged { //aka mefServiceUniCfgCeVidUntagged
		type msea:vlan-id-type;
	
		description
		"Configures the CE VLAN ID associated with untagged and priority
		Service Frames. It allows the identification of untagged and
		priority tagged traffic with a specific CE-VLAN ID. This object
		is ignored for all to one bundling at the UNI.
		This attribute has been placed on the interface (rather than the UNI)
		as it can be defined regardless of whether a UNI exists or not";
		reference
		"[MEF 6.1] 6.0, [MEF 7.2] 6.2.1.2";
	  }
	
	  leaf ce-priority-untagged { //aka mefServiceUniCfgCePriorityUntagged
		type msea:priority-type;
	
		description
		"Configures the CE VLAN Priority associated with untagged Service
		Frames. It allows the assignment of a specific VLAN priority to
		untagged traffic. This object is ignored for all to one bundling
		at the UNI.
		This attribute has been placed on the interface (rather than the UNI)
		as it can be defined regardless of whether a UNI exists or not";
		reference
		"[MEF 7.2] 6.2.1.2";
	  }

      leaf admittance-criteria {
    	  type enumeration {
			enum admitAll { description "Admit all frames";}
			enum admitPrioUntaggedOnly { description "Admit only frames that are not Priority tagged";}
			enum admitVlanOnly { description "Admit only frames that are VLAN tagged";}
    	  }
    	  
//    	  default admitAll; 
    	  
    	  description "Criteria for admitting packets to this interface. 
    			  The Frame Format attribute to determintes how frames are tagged";
      }
      
    } //End augment "/if:interfaces/if:interface


  augment "/if:interfaces-state/if:interface" {

      leaf max-vc { //aka mefServiceInterfaceStatusMaxVc
        type uint32 {
          range "1..4095";
        }
        description 
         "This object indicates the maximum number of virtual channels that the
          interface can support. A virtual connection can be an Ethernet Virtual 
          Connection (EVC) or an Operator Virtual Connection (OVC) depending upon
          the type of interface that is selected.  ";
        reference   
         "[MEF 6.1] 6.0; [MEF 7.2] 6.2.1.2";
      }

      leaf max-end-point-per-vc { //aka mefServiceInterfaceStatusMaxEndPointPerVc
        type uint32 {
          range "1..10";
        }
        description 
         "This object indicates the interface maximum number of end points per
          virtual channel. It can be used to indicate the maximum number of OVC
          end points per OVC. It has no current applicability for EVCs. ";
        reference   
         "[MEF 26.1]";
      }
    } //End augment "/if:interfaces-state/if:interface"


  augment "/if:interfaces-state/if:interface/if:statistics" {

      leaf ingress-undersized { //aka mefServiceInterfaceStatisticsIngressUndersized
        type yang:counter32;
        units "Ethernet frames";
        description 
         "This object is incremented for each frame received
          on a NE interface that was smaller than 64 octets.
          
          This object defaults to '0'. ";
        reference   
         "[MEF 15] 8.2; [Q.840.1] 6.2.4";
      }

      leaf ingress-oversized { //aka mefServiceInterfaceStatisticsIngressOversized
        type yang:counter32;
        units "Ethernet frames";
        description 
         "This object is incremented for each frame received
          on a NE interface that was larger than the maximum MTU size.
          
          This object defaults to '0'.";
        reference   
         "[MEF 15] 8.2; [Q.840.1] 6.2.4";
      }

      leaf ingress-fragments { //aka mefServiceInterfaceStatisticsIngressFragments
        type yang:counter32;
        units "Ethernet frames";
        description 
         "This object is incremented for each frame received
          on a NE interface that was less than 64 octets in length
          (excluding framing bits but including FCS octets) and had 
          either a bad Frame Check Sequence (FCS) with an integral 
          number of octets (FCS Error) or a bad FCS with a non-integral
          number of octets (Alignment Error).
          
          Note that it is entirely normal for this counter to
          increment.  This is because it counts both runts (which are
          normal occurrences due to collisions) and noise hits.
          
          This object defaults to '0'.";
        reference   
         "[MEF 15] 8.2; [Q.840.1] 6.2.4";
      }

      leaf ingress-crc-alignment { //aka mefServiceInterfaceStatisticsIngressCrcAlignment
        type yang:counter32;
        units "Ethernet frames";
        description 
         "This object is incremented for each frame received
          on a NE interface that was from 64 octets to the maximum MTU
          size in length, but had either a bad Frame Check Sequence (FCS)
          with an integral number of octets (FCS Error) or a bad FCS with
          a non-integral number of octets (Alignment Error).
          
          This object defaults to '0'.";
        reference   
         "[MEF 15] 8.2; [Q.840.1] 6.2.4";
      }

      leaf ingress-invalid-vid { //aka mefServiceInterfaceStatisticsIngressInvalidVid
        type yang:counter32;
        units "Ethernet frames";
        description 
         "This object is incremented for each frame received
          on a NE interface with an invalid VLAN ID.
          
          This object defaults to '0'.";
        reference   
         "[MEF 15] 8.2; [Q.840.1] 6.2.4";
      }

      leaf ingress-octets { //aka mefServiceInterfaceStatisticsIngressOctets
        type yang:counter64;
        units "octets";
        description 
         "This object is incremented by the number of octets in a
          valid frame received on a NE interface.
          
          This object defaults to '0'.";
        reference   
         "[MEF 15] 8.2; [Q.840.1] 6.2.4";
      }

      leaf ingress-unicast { //aka mefServiceInterfaceStatisticsIngressUnicast
        type yang:counter64;
        units "Ethernet frames";
        description 
         "This object is incremented for each valid unicast frame received
          on a NE interface.
          
          NEs that do not support 64 bit counters can return the
          upper half of the counter as all zeros.
          
          This object defaults to '0'.";
        reference   
         "[MEF 15] 8.2; [Q.840.1] 6.2.4";
      }

      leaf ingress-multicast { //aka mefServiceInterfaceStatisticsIngressMulticast
        type yang:counter64;
        units "Ethernet frames";
        description 
         "This object is incremented for each valid multicast frame received
          on a NE interface.
          
          ME-NEs that do not support 64 bit counters can return the
          upper half of the counter as all zeros.
          
          This object defaults to '0'.";
        reference   
         "[MEF 15] 8.2; [Q.840.1] 6.2.4";
      }

      leaf ingress-broadcast { //aka mefServiceInterfaceStatisticsIngressBroadcast
        type yang:counter64;
        units "Ethernet frames";
        description 
         "This object is incremented for each valid broadcast frame received
          on a NE interface.
          
          ME-NEs that do not support 64 bit counters can return the
          upper half of the counter as all zeros.
          
          This object defaults to '0'.";
        reference   
         "[MEF 15] 8.2; [Q.840.1] 6.2.4";
      }

      leaf egress-octets { //aka mefServiceInterfaceStatisticsEgressOctets
        type yang:counter64;
        units "octets";
        description 
         "This object is incremented by the number of octets in a frame 
          transmitted on a NE interface.
          
          This object defaults to '0'.";
        reference   
         "[MEF 15] 8.2; [Q.840.1] 6.2.4";
      }

      leaf egress-unicast { //aka mefServiceInterfaceStatisticsEgressUnicast
        type yang:counter64;
        units "Ethernet frames";
        description 
         "This object is incremented for each unicast frame transmitted on a
          NE interface.
          
          ME-NEs that do not support 64 bit counters can return the
          upper half of the counter as all zeros.
          
          This object defaults to '0'.";
        reference   
         "[MEF 15] 8.2; [Q.840.1] 6.2.4";
      }

      leaf egress-multicast { //aka mefServiceInterfaceStatisticsEgressMulticast
        type yang:counter64;
        units "Ethernet frames";
        description 
         "This object is incremented for each multicast frame transmitted on a
          NE interface.
          
          ME-NEs that do not support 64 bit counters can return the
          upper half of the counter as all zeros.
          
          This object defaults to '0'.";
        reference   
         "[MEF 15] 8.2; [Q.840.1] 6.2.4";
      }

      leaf egress-broadcast { //aka mefServiceInterfaceStatisticsEgressBroadcast
        type yang:counter64;
        units "Ethernet frames";
        description 
         "This object is incremented for each broadcast frame transmitted on a
          NE interface.
          
          ME-NEs that do not support 64 bit counters can return the
          upper half of the counter as all zeros.
          
          This object defaults to '0'.";
        reference   
         "[MEF 15] 8.2; [Q.840.1] 6.2.4";
      }
    } //End augment "/if:interfaces-state/if:interface/if:statistics
  
  
  augment "/if:interfaces-state" {
	  leaf mef-service-type-options { //aka mefServiceInterfaceStatusType
		type MefServiceInterfaceType;
		description 
		 "This object is a vector of bits that indicates the possible
		  interface types that an interface can be configured to. An interface,
		  for instance, can be configured to be a UNI type 1 or 2, or an ENNI.
		  
		  All the possible capabilities of an interface are indicated, one bit
		  per possible type. At least one bit must be set for MEF compliant NEs.";
		reference   
		 "[MEF 6.1] 6.0";
	  }
  } //End augment "/if:interfaces-state

  
  
  augment "/if:interfaces" {
      leaf l2cp-group-index { //aka mefServiceInterfaceCfgL2cpGrpIndex
        type leafref {
          path "/if:interfaces/msea-if:interface-profiles/msea-if:l2cp-group/msea-if:group-index";
        }
        description 
         "This object is the index of the L2CP profile group
          (mefServiceL2cpGrpCfgIndex) associated with the current interface. A 
          value of 0 indicates that no interface L2CP profile group is associated
          with the interface. The L2CP group must be the same for both interfaces";
        reference   
         "[MEF 6.1] 6.0; [MEF 6.1.1] 8.0; [MEF 7.2] 6.2.1.2";
        
//        must "count(//if:interfaces/if:interface[msea-if:l2cp-group-index = current()]) = 2" {
//        	  error-app-tag "msea-if-must-01";
//        	  error-message "The same L2CP Group must be used on both interfaces of this device";
//          }
      }

      leaf mef-service-type { //aka mefServiceInterfaceCfgType
        type MefServiceInterfaceType;
        description 
         "This object indicates the configured interface type. One
          bit in the vector can be set at one time based upon the
          possible values indicated by mefServiceInterfaceStatusType.";
	    //default bUni1d1; --These defaults break the validation - not using them in Eagle
        reference   
         "[MEF 6.1] 6.0; [MEF 7.2] 6.2.1.1, 6.2.1.2, 6.2.1.3";
      }
      
      
	container interface-profiles {

		list interface-bwp-group { //aka mefServiceBwpGrpCfgEntry

			key "group-index";
			max-elements 64;
			description
			"Bandwidth profile group settings table entry.";

			leaf group-index { //aka mefServiceBwpGrpCfgIndex
				type uint8;
				description
				"Bandwidth profile group index number";
			}

			list interface-bwp { //aka mefServiceBwpCfgEntry
				key "cos-index";//Changed to cos-index (from bwp-index) based on MEP 40 6.4.2 
				unique name;
				max-elements 64;
				
				description
				"Bandwidth profile. This maps 1:1 with a COS instance. This object is 
				maintained here to keep the traditional layout of BWPGroup-BWP-COS, but does 
				not have any other purpose in the current implementation";

				leaf cos-index { //aka mefServiceBwpCfgCosIndex
					type leafref {
						path "/if:interfaces/msea-if:interface-profiles/msea-if:interface-cos/msea-if:cos-index";
					}
					description
					"This object is the index number of the CoS ID profile
					associated with the current bandwidth profile. A value of 0 indicates
					that no CoS ID profile is associated with the bandwidth profile and the
					bandwidth profile applies to all CoS IDs.

					This index indicates a specific CoS ID profile previously configured via
					mefServiceCosCfgTable as indicated by the mefServiceCosCfgIndex object.";
					reference
					"[MEF 6.1] 6.1; [MEF 7.2] 6.2.1.3";
					
					must "current()/../../msea-if:group-index > 0" {
						error-app-tag "msea-if-must-02";
						error-message "No BWP's can be added to the Bandwidth Profile Group 0, as this index represents a special case";
					}
				}

				leaf name { //mefServiceBwpCfgIdentifier
					type string {
						length "1..45";
					}
					mandatory true;
					description
					"This object indicates the bandwidth profile identifier for the
					associated bandwidth profile index and is an arbitrary
					text string that is used to identify a bandwidth profile. Unique
					string values are chosen to uniquely identify the bandwidth
					profile.

					Octet values of 0x00 through 0x1f are illegal.

					MEF 26.1 restricts the maximum size identifiers to 45 octets.";
					reference
					"[MEF 6.1] 6.0, 6.1, 6.2, 6.3; [MEF 7.2] 6.2.1.2, 6.2.1.3";
				}
// The attributes of BWP Group are not made visible here as they are not used in the device
//				leaf committed-information-rate { //aka mefServiceBwpCfgCir
//					type uint32 {
//						range "0..10000000";
//					}
//					units "kbits/s";
//					default 1000000;
//					msea:not-changeable;
//					
//					description
//					"This object indicates the Committed Information Rate (CIR) in kbits/s
//					and defines the average rate in kbits/sec up to which
//					the network delivers Service Frames. Service Frames that meet
//					the CIR are said to be in profile or in conformance to performance
//					objectives. These frames are generally identified as 'Green' 
//					Service Frames.";
//					reference
//					"[MEF 6.1] 6.0, 6.1, 6.2, 6.3; [MEF 7.2] 6.2.1.2, 6.2.1.3";
//				}
//
//				leaf committed-burst-size { //aka mefServiceBwpCfgCbs
//					type uint32 {
//						range "0..10000000";
//					}
//					units "bytes";
//					default 12;
//					msea:not-changeable;
//
//					description
//					"This object indicates the Committed Burst Size (CBS) in bytes. It limits
//					the maximum number of bytes available for a burst of Service Frames sent
//					at interface speed to remain CIR-conformant.";
//					reference
//					"[MEF 10.2]";
//				}
//
//				leaf excess-information-rate { //aka mefServiceBwpCfgEir
//					type uint32 {
//						range "0..10000000";
//					}
//					units "kbits/s";
//					msea:not-changeable;
//
//					description
//					"This object indicates the Excess Information Rate (EIR) in kbits/s
//					and defines the average rate in kbits/sec of Service Frames up to
//					which the network may deliver Service Frames but without performance
//					objectives. Service Frames that meet the EIR as set to be in out-of-
//					profile or not in conformance to performance objectives. These
//					frames are not guaranteed to be delivered and are generally identified
//					as 'Yellow' service frames.";
//					reference
//					"[MEF 6.1] 6.0, 6.1, 6.2, 6.3; [MEF 7.2] 6.2.1.2, 6.2.1.3";
//				}
//
//				leaf excess-burst-size { //aka mefServiceBwpCfgEbs
//					type uint32 {
//						range "0..10000000";
//					}
//					units "bytes";
//					msea:not-changeable;
//
//					description
//					"This object indicates the Excess Burst Size (EBS) in bytes. It limits
//					the maximum number of bytes available for a burst of Service Frames
//					sent at the interface speed to remain EIR-conformant.";
//					reference
//					"[MEF 6.1] 6.0, 6.1, 6.2, 6.3; [MEF 7.2] 6.2.1.2, 6.2.1.3";
//				}
//
//				leaf color-mode { //aka mefServiceBwpCfgCm
//					type enumeration {
//						enum colorBlind {description "A bandwidth profile property where ingress 
//							Service Frames are not pre-colored for either
//							green or yellow, and if present, is ignored when
//							determining the level of compliance for each
//							Service Frame";
//						}
//						
//						enum colorAware {
//							description "A bandwidth profile property were a pre-determined
//							level of Bandwidth Profile compliance for each
//							Service Frame is taken into account when determining
//							the level of compliance for each Service Frame.
//							Each service frame can be colored red (discarded),
//							yellow (conditional delivery), or green (unconditional
//							delivery.";
//						}
//					}
//					default colorBlind;
//					msea:not-changeable;
//
//					description
//					"This object configures the bandwidth profile color mode.";
//
//					reference
//					"[MEF 6.1] 6.0, 6.1, 6.2, 6.3; [MEF 7.2] 6.2.1.2, 6.2.1.3";
//				}
//
//				leaf coupling-flag { //aka mefServiceBwpCfgCf
//					type enumeration {
//						enum couplingYellowEirOnly {
//							description "The long term average bit rate of Service
//							Frames that are declared Yellow is bounded by EIR."; 
//						}
//
//						enum couplingYellowEirPlusCir {
//							description "The long term average bit rate of Service
//							Frames that are declared Yellow is bounded
//							by CIR + EIR depending on the volume of
//							the offered Service Frames that are
//							declared Green.";
//						}
//					}
//					
//					default couplingYellowEirOnly;
//					msea:not-changeable;
//
//					description
//					"This object configures the bandwidth profile coupling flag and has
//					the effect of controlling the volume of the Service Frames that are
//					declared Yellow.";
//
//					reference
//					"[MEF 6.1] 6.0, 6.1, 6.2, 6.3; [MEF 7.2] 6.2.1.2, 6.2.1.3";
//				}
//
//				container performance { //aka mefServicePerformanceEntry
//					config false;
//					description
//					"Traffic Performance Data Set profile settings table entry.";
//
//					leaf ingress-green-frames { //aka mefServicePerformanceIngressGreenFrameCount
//						type yang:counter64;
//						units "Ethernet frames";
//
//						description
//						"This object indicates the number of green frames that were 
//						received on a ME-NE for the associated bandwidth profile.
//
//						ME-NEs that do not support 64 bit counters can return the
//						upper half of the counter as all zeros.
//
//						This object defaults to '0'. ";
//						reference
//						"[MEF 15] 8.2; [Q.840.1] 6.2.4";
//					}
//
//					leaf ingress-yellow-frames { //aka mefServicePerformanceIngressYellowFrameCount
//						type yang:counter64;
//						units "Ethernet frames";
//
//						description
//						"This object indicates the number of yellow frames that were 
//						received on the ME-NE for the associated bandwidth profile.
//
//						ME-NEs that do not support 64 bit counters can return the
//						upper half of the counter as all zeros.
//
//						This object defaults to '0'. ";
//						reference
//						"[MEF 15] 8.2; [Q.840.1] 6.2.4";
//					}
//
//					leaf ingress-red-frames { //aka mefServicePerformanceIngressRedFrameCount
//						type yang:counter64;
//						units "Ethernet frames";
//						description
//						"This object indicates the number of red frames that were 
//						received on the ME-NE for the associated bandwidth profile.
//
//						ME-NEs that do not support 64 bit counters can return the
//						upper half of the counter as all zeros.
//
//						This object defaults to '0'. ";
//						reference
//						"[MEF 15] 8.2; [Q.840.1] 6.2.4";
//					}
//
//
//					leaf ingress-green-frame-discards { //aka mefServicePerformanceIngressGreenFrameDiscards
//						type yang:counter64;
//						units "Ethernet frames";
//						description
//						"This object indicates the number of green frames that were 
//						discarded due to congestion within the ME-NE for the
//						associated bandwidth profile.
//
//						ME-NEs that do not support 64 bit counters can return the
//						upper half of the counter as all zeros.
//
//						This object defaults to '0'. ";
//						reference
//						"[MEF 15] 8.2; [Q.840.1] 6.2.4";
//					}
//
//					leaf ingress-yellow-frame-discards { //aka mefServicePerformanceIngressYellowFrameDiscards
//						type yang:counter64;
//						units "Ethernet frames";
//						description
//						"This object indicates the number of yellow frames that were 
//						discarded due to congestion within the ME-NE for the
//						associated bandwidth profile.
//
//						ME-NEs that do not support 64 bit counters can return the
//						upper half of the counter as all zeros.
//
//						This object defaults to '0'. ";
//						reference
//						"[MEF 15] 8.2; [Q.840.1] 6.2.4";
//					}
//
//					leaf ingress-octets-discards {
//						type yang:counter64;
//						units "octets";
//						description
//						"This object indicates the number of valid octets of any colour 
//						that were discarded due to congestion within the ME-NE for the
//						associated bandwidth profile.
//
//						This object defaults to '0'. ";
//						reference
//						"[MEF 15] 8.2; [Q.840.1] 6.2.4";
//					}
//					
//				} //End performance

			} //End bwp

		} //End bwp-group
		
		list interface-cos { //aka mefServiceCosCfgEntry
			key "cos-index";
			unique name;
			max-elements 64;
			description
			"Class of Service Identifier settings table entry.";

			leaf cos-index { //aka mefServiceCosCfgIndex
				type uint32 {
					range 1..max;
				}
				description
				"Class of Service Identifier profile index number.";
			}

			leaf name { //aka mefServiceCosCfgIdentifier
				type string {
					length 1..45;
				}
				
				description
				"This object indicates the Class of Service Name for the
				associated CoS profile index and is an arbitrary text string that is
				used to identify a CoS ID profile. Unique string values are chosen to
				uniquely identify the profile.

				Octet values of 0x00 through 0x1f are illegal.

				MEF 26.1 restricts the maximum size identifiers to 45 octets.";
				reference
				"[MEF 6.1] 6.0, 6.1, 6.2, 6.3; [MEF 7.2] 6.2.1.2, 6.2.1.3";
			}
			
			container dscp-cos-type {
				description "Indicates that the CoS profile is associated
				with the incoming frame's DSCP field if it is an IP frame. 
				If it is not an IP frame no action is taken on it";
				
				choice dscp-id-choice {
					case dscp-bits-list {
						leaf dscp-group-bit-list {
							type bits {
								bit dscp-0-7 {
									description "The set of DSCP identifiers from 0-7";
								}
								bit dscp-8-15 {
									description "The set of DSCP identifiers from 8-15";
								}
								bit dscp-16-23 {
									description "The set of DSCP identifiers from 16-23";
								}
								bit dscp-24-31 {
									description "The set of DSCP identifiers from 24-31";
								}
								bit dscp-32-39 {
									description "The set of DSCP identifiers from 32-39";
								}
								bit dscp-40-47 {
									description "The set of DSCP identifiers from 40-47";
								}
								bit dscp-48-55 {
									description "The set of DSCP identifiers from 48-55";
								}
								bit dscp-56-63 {
									description "The set of DSCP identifiers from 56-63";
								}
							}
						}
					}

					case dscp-0-63 {
						container dscp-0-63 {
							presence "The full set of DSCP identifiers from 0-63";
						}
					}

					case specific-values {
						leaf-list dscp-id {
							type uint16 {
								range 0..64;
							}
							ordered-by system;
							description "The set of DSCP identifiers handled by this COS";
						}
					}
					mandatory true;
					msea:not-changeable;
				}
				
				choice color-specification {
					case all-green {
						container color-all-green {
							presence "Color for all specified DSCPs mapped to green";
						}
					}
					case all-yellow {
						container color-all-yellow {
							presence "Color for all specified DSCPs mapped to yellow";
						}
					}
					case all-dropped {
						container color-all-dropped {
							presence "Color for all specified DSCPs mapped to dropped";
						}
					}
					
					case dscp-to-color-map {
						list dscp-color {
							key dscp-id;
							ordered-by system;
							description "A list of DSCP values that apply to this COS.
							When the COS type is DSCP a subset of the values can 
							be specified. Other DSCP values can be specified in 
							additional COS profiles. In total the same priority
							cannot be repeated in a BWP Group";
		
							leaf dscp-id {
								type uint16 {
									range 0..64;
								}
							}
							
							leaf color {
								description "Color to apply to incoming IP frames
								with this DSCP id";
								
								type msea:cos-color-type;
							}
						}
					}
					default all-green;
					msea:not-changeable;
				}
			}
			
			leaf outgoing-cos-value {
			  type msea:priority-type;
			  mandatory true;
			  msea:not-changeable;

		      description
		        "Used to set the egress COS to use for all ingress COS explicitly listed";
		      reference   
				 "Edge Assure internal API";
		    }
		}

		
		list l2cp-group { //aka mefServiceL2cpGrpCfgEntry
			key "group-index";
			max-elements 64;
			description
			"L2CP profile group settings table entry on an interface.";

			leaf group-index { //aka mefServiceL2cpGrpCfgIndex
				type uint32;
				description
				"L2CP profile group index number, indicating the specific L2CP profile 
				group";
			}

			list l2cp { //aka mefServiceL2cpCfgEntry
				key "index";
				max-elements 64;
				description
				"L2CP settings table entry on an interface or a service.";

				leaf index { //aka mefServiceL2cpCfgIndex
					type uint32;
					description
					"This object configures the L2CP index number on an interface or a 
					Service and is used to create/access a L2CP profile within a L2CP
					group.";

					must "current()/../../msea-if:group-index > 0" {
						error-app-tag "msea-if-must-03";
						error-message "No L2CP's can be added to the L2CP Group 0, as this index represents a special case";
					}
				}

				leaf handling { //aka mefServiceL2cpCfgType
					type enumeration {
						enum discard {description "The indicated L2CP is discarded";}
						
						enum tunnel {description "The indicated L2CP is tunneled (passed)";}
						
						enum peer {description "The indicated L2CP is peered with the NE";}
						
//						enum passToEvc {description "the indicated L2CP is passed to the EVC for
//							EVC processing of the L2CP. Final L2CP
//							disposition is based the L2CP profile for
//							the EVC to be tunneled, discarded, or peered.
//							This value is not valid for EVC based L2CP";
//						}
					}
					default tunnel;
					msea:not-changeable;
					
					description
					"This object configures the handling of matching L2CP frames.";
					reference
					"[MEF 6.1] 6.0, 8.0; [MEF 6.1.1] 8.0; [MEF 7.2] 6.2.1.2";
				}

				leaf match-scope { //aka mefServiceL2cpCfgMatchScope
					type l2cp-destination-address;
					default destinationAddressOnly;
					msea:not-changeable;
					
					description
					"This object configures the L2CP selection matching scope.";
					reference
					"[MEF 6.1] 6.0, 8.0; [MEF 6.1.1] 8.0; [MEF 7.2] 6.2.1.2";
					
				}

				leaf mac-address { //aka mefServiceL2cpCfgMacAddress
					type l2cp-dest-mac-address;
					mandatory true;
					msea:not-changeable;
					
					description
					"This object configures the L2CP Destination MAC address.

					Valid values are 01-80-C2-00-00-00 through 01-80-C2-00-00-0F and
					01-80-C2-00-00-20 through 01-80-C2-00-00-2F";

					must "count(current()/../../msea-if:l2cp[msea-if:mac-address = current()]) <= 1" {
						error-app-tag "msea-if-must-04";
						error-message "A destination address can only appear once in an L2CP Group";
					}
				}
			} //End l2cp

		} //End l2cp-group

		
	} //End profiles
  } //end augment interfaces
  
} /* end of module msea-uni-evc-interface */
