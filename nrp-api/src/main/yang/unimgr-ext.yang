module unimgr-ext {
    namespace "urn:odl:unimgr:yang:unimgr-ext";
    prefix unimgr-ext;

    import tapi-common {
        prefix tapi-common;
    }
    import tapi-topology {
        prefix tapi-topology;
    }
    import nrp-interface {
        prefix nrp-interface;
    }
    import mef-common-types {
        prefix mef-common-types;
    }
    import yang-ext {
        prefix "ext";
    }
    revision 2017-05-31 {
        description "Unimgr SIP extensions";
    }


    rpc add-sip {
        description "Add sip to the existing nep";
        input {
            leaf nep-id {
                type leafref {
                    path '/tapi-common:context/tapi-topology:topology/tapi-topology:node/tapi-topology:owned-node-edge-point/tapi-topology:uuid';
                }
            }
            leaf node-id {
                type leafref {
                    path '/tapi-common:context/tapi-topology:topology/tapi-topology:node/tapi-topology:uuid';
                }
            }
            choice sip-type {
                container uni-spec {
                    uses nrp-interface:nrp-carrier-eth-uni-n-resource;
                    description "none";
                }
                container inni-spec {
                    uses nrp-interface:nrp-carrier-eth-inni-n-resource;
                    description "none";
                }
                container enni-spec {
                    uses nrp-interface:nrp-carrier-eth-enni-n-resource;
                    description "none";
                }
            }
        }
    }

    augment "/tapi-common:context/tapi-topology:topology/tapi-topology:node" {
        leaf activation-driver-id {
            type string;
        }
        ext:augment-identifier "node-adi-augmentation";
    }

    augment "/tapi-common:context/tapi-topology:topology/tapi-topology:node" {
        list service-vlan-map {
            key "service-id";
            leaf service-id {
                type string;
            }
            leaf vlan-id {
                type mef-common-types:positive-integer;
            }
        }
        ext:augment-identifier "node-svm-augmentation";
    }
}
