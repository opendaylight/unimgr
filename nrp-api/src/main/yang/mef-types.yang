module mef-common-types {
    namespace "urn:mef:yang:MEF_Types";
    prefix mef-common-types;
    organization "Metro Ethernet Forum (MEF)";
    contact "MEF";
    description "none";
    revision 2017-05-31 {
        description "MEF NRP 1.0.alpha";
        reference "ONF-TR-527, ONF-TR-512, ONF-TR-531, RFC 6020 and RFC 6087";
    }
    /***********************
    * package type-definitions
    **********************/ 
        typedef admin-state {
            type enumeration {
                enum unlocked {
                    description "The resource is administratively permitted to perform services for its users.";
                }
                enum locked {
                    description "The resource is administratively prohibited from performing services for its users.";
                }
            }
            description "This enumeration is for Administrative states. Refer to ITU-T X.731.";
        }
        grouping agg-link-depth-g {
            container vlan-id {
                uses vlan-id-g;
                description "The ingress frame Vlan ID. ";
            }
            leaf link-depth {
                type positive-integer;
                description "The number of links for the aggregation link.";
            }
            description "This is a pair of <VLAN ID, link depth> indicating that a given VLAN ID maps to a given number of links in the Port Conversation ID to Aggregation Link Map.";
        }
        typedef available-meg-level {
            type enumeration {
                enum none {
                    description "Indicates that SOAM EI Frames are not guaranteed to pass over this OVC at any MEG Level.";
                }
                enum 0 {
                    description "none";
                }
                enum 1 {
                    description "none";
                }
                enum 2 {
                    description "none";
                }
                enum 3 {
                    description "none";
                }
                enum 4 {
                    description "none";
                }
                enum 5 {
                    description "none";
                }
                enum 6 {
                    description "none";
                }
                enum 7 {
                    description "none";
                }
            }
            description "This enumeration is for available MEG level, can be either NONE or value 0..7.  NONE indicates that SOAM EI Frames are not guaranteed to pass over at any MEG Level.";
        }
        typedef color-field-type {
            type enumeration {
                enum pcp {
                    description "Using PCP field to map to the color.";
                }
                enum dei {
                    description "Using DEI field to map to the color.";
                }
                enum end-point {
                    description "Using EVC End Point or the OVC End Point to map to the color.";
                }
                enum dscp {
                    description "Using DSCP field to map to the color.";
                }
            }
            description "This enumeration is for selecting which frame field being used for color indication.";
        }
        typedef color-mode {
            type enumeration {
                enum color-aware {
                    description "none";
                }
                enum color-blind {
                    description "none";
                }
            }
            description "This enumeration indicates whether the Color Identifier of the Service Frame is considered by the Bandwidth Profile Algorithm.";
        }
        typedef connection-type {
            type enumeration {
                enum point-to-point {
                    description "none";
                }
                enum multipoint {
                    description "none";
                }
                enum rooted-multipoint {
                    description "none";
                }
            }
            description "This is for EVC or OVC connection types, including point to point, multi-point and rooted multi-point.";
        }
        grouping conversation-id-to-aggregation-link-map-g {
            leaf conversation-id {
                type natural-number;
                description "The conversation ID is a Vlan ID or 0 for untagged or priority tagged frame.. ";
            }
            leaf-list link-id-list {
                type natural-number;
                min-elements 1;
                description "The link ID of the aggregation link.";
            }
            description "This is a Port Conversation ID to Aggregation Link Map as defined in IEEE Std 802.1AX – 2014.";
        }
        typedef cos-or-eec-mapping-type {
            type enumeration {
                enum end-point {
                    description "Using EVC End Point or OVC End Point to map to the CoS Name as CoS ID.";
                }
                enum pcp {
                    description "Using PCP field to map to the CoS Name as CoS ID.";
                }
                enum dscp {
                    description "Using DSCP field to map to the CoS Name as CoS ID.";
                }
            }
            description "This lists the Class of Service identifier type, or the Equivalence Class Identifier type. ";
        }
        typedef dei-or-discard {
            type enumeration {
                enum discard {
                    description "Discard the egress frame when the Egress Map determines based on CoS Name (and ingress Color).";
                }
                enum 0 {
                    description "Set  egress frame DEI field to be 0 when the Egress Map determines based on CoS Name (and ingress Color).";
                }
                enum 1 {
                    description "Set  egress frame DEI field to be 1 when the Egress Map determines based on CoS Name (and ingress Color).";
                }
            }
            description "This lists the DEI value for color or discard, used for Egress Map.";
        }
        typedef egress-map-type {
            type enumeration {
                enum cn-c-tag-pcp {
                    description "CoS Name to C-Tag PCP egress map type";
                }
                enum cc-c-tag-pcp {
                    description "CoS Name and Color to C-Tag PCP egress map type";
                }
                enum cc-c-tag-dei {
                    description "CoS Name and Color to C-Tag DEI egress map type";
                }
                enum cn-s-tag-pcp {
                    description "CoS Name to S-Tag PCP egress map type";
                }
                enum cc-s-tag-pcp {
                    description "CoS Name and Color to S-Tag PCP egress map type";
                }
                enum cc-s-tag-dei {
                    description "CoS Name and Color to S-Tag DEI egress map type";
                }
            }
            description "This lists the Egress Map types, either CoS Name to PCP, or CoS Name and Ingress Color to PCP, or  CoS Name and Ingress Color to DEI for S-Tag or C-Tag.";
        }
        typedef ethernet-frame-format {
            type enumeration {
                enum ethernet {
                    description "none";
                }
            }
            description "This is a single value read only attribute. Keep this in the info model just because MEF 10.3 lists it as a service attribute.";
        }
        typedef evc-end-point-role {
            type enumeration {
                enum root {
                    description "EVC End Point has role of root for the EVC.";
                }
                enum leaf {
                    description "EVC End Point has role of leaf for the EVC.";
                }
            }
            description "The value indicates how external interface frames mapped to the  EVC End Point can be forwarded.";
        }
        typedef frame-color {
            type enumeration {
                enum green {
                    description "none";
                }
                enum yellow {
                    description "none";
                }
            }
            description "Frame color is either Green or Yellow.";
        }
        typedef frame-delivery {
            type enumeration {
                enum discard {
                    description "Frame must be discarded.";
                }
                enum conditionally {
                    description "Frame will be delivered with specified condition.";
                }
                enum unconditionally {
                    description "Frame will be delivered unconditionally.";
                }
            }
            description "Service frame delivery defined in MEF 10.3. When the value is conditionally, the specific condition has to be addresses by the users. What conditions should be supported are not in the scope.";
        }
        typedef identifier45 {
            type string;
            description "Unique by network administrative domain, containing no more than 45 characters and non-null RFC Display String but not contain the characters 0x00 through 0x1f.";
        }
        typedef identifier90 {
            type string;
            description "Unique by network administrative domain, containing no more than 90 characters and non-null RFC Display String but not contain the characters 0x00 through 0x1f.";
        }
        typedef interface-resiliency {
            type enumeration {
                enum none {
                    description "none";
                }
                enum 2-link-active-standby {
                    description "none";
                }
                enum all-active {
                    description "none";
                }
                enum other {
                    description "none";
                }
            }
            description "The method for protection, if any, against a physical link failure. Refer to MEF 10.3.2 and MEF 26.2.";
        }
        typedef ip-version {
            type enumeration {
                enum ipv4 {
                    description "none";
                }
                enum ipv6 {
                    description "none";
                }
                enum ipv4-and-ipv6 {
                    description "none";
                }
            }
            description "This enumeration lists the IP versions, including IPv4, IPv6 and both.";
        }
        typedef l2cp-address-set {
            type enumeration {
                enum cta {
                    description "CE-Vlan Tag Aware";
                }
                enum ctb {
                    description "CE-Vlan Tag Blind";
                }
                enum ctb2 {
                    description "CE-Vlan Tag Blind option 2";
                }
            }
            description "This lists the L2CP Address Set. Refer to MEF 45.";
        }
        grouping l2cp-peering-g {
            container protocol-id {
                uses l2cp-protocol-g;
                description "This is a L2CP Protocol Identifier.";
            }
            leaf destination-address {
                type natural-number;
                description "This is a Mac Address.";
            }
            leaf-list link-id-list {
                type positive-integer;
                description "It is possible that a protocol (e.g. ESMC) could operate on some, but not all, of the physical
                    links. When linkId is not listed, the protocol peering applies to all members of the aggregation link.";
            }
            description "This is a list specifies the L2CP Protocol Identifier and the Destination Address in use by the protocol entity.";
        }
        grouping l2cp-protocol-g {
            leaf l2cp-protocol-type {
                type l2cp-protocol-type;
                description "This attribute specifies the type of L2CP protocol, i.e., LLC or EtherType.";
            }
            leaf llc-address-or-ether-type {
                type natural-number;
                description "This attribute specifies the LLC address or the EtherType value.";
            }
            leaf sub-type {
                type natural-number;
                description "This attribute specifies the subtype of the L2CP protocol.";
            }
            description "This data type defines a L2CP protocol (LLC address type or EtherType) with possible subtype.";
        }
        typedef l2cp-protocol-type {
            type enumeration {
                enum ethertype {
                    description "EtherType for L2CP, e.g., LLDP (0x88CC).";
                }
                enum llc {
                    description "Logical Link Control sublayer address for L2CP, e.g., STP (0x42).";
                }
            }
            description "This lists the L2CP protocol types, either EtherType, or LLC Address.";
        }
        typedef mep-direction {
            type enumeration {
                enum down {
                    description "none";
                }
                enum up {
                    description "none";
                }
            }
            description "This is for MEP direction, either Down MEP or Up MEP.";
        }
        grouping mep-level-and-direction-g {
            leaf level {
                type natural-number;
                description "This is the MEG level, value between 0..7.";
            }
            leaf direction {
                type mep-direction;
                description "This is MEP direction, UP or DOWN.";
            }
            description "This complex data type includes MEG LEVEL and MEP direction.";
        }
        typedef natural-number {
            type int64;
            description "An integer >=0";
        }
        typedef operational-state {
            type enumeration {
                enum enabled {
                    description "none";
                }
                enum disabled {
                    description "none";
                }
            }
            description "This enumeration is for Operational states. Refer to ITU-T X.731.";
        }
        typedef ovc-end-point-map-form {
            type enumeration {
                enum form-e {
                    description "OVC End Point Map for ENNI.";
                }
                enum form-v {
                    description "OVC End Point Map for VUNI.";
                }
                enum form-u {
                    description "OVC End Point Map for UNI.";
                }
                enum form-t {
                    description "OVC End Point Map for Trunk.";
                }
            }
            description "The OVC End Point Map types, for ENNI (FORM E), for UNI (FORM U), for VUNI (FORM V), or for Trunk (FORM T).";
        }
        typedef ovc-end-point-role {
            type enumeration {
                enum root {
                    description "OVC End Point has role of root for the OVC.";
                }
                enum leaf {
                    description "OVC End Point has role of leaf for the OVC.";
                }
                enum trunk {
                    description "OVC End Point has role of trunk for the OVC.";
                }
            }
            description "The value indicates how external interface frames mapped to the  OVC End Point can be forwarded.";
        }
        typedef pcp-or-discard {
            type enumeration {
                enum discard {
                    description "none";
                }
                enum 0 {
                    description "none";
                }
                enum 1 {
                    description "none";
                }
                enum 2 {
                    description "none";
                }
                enum 3 {
                    description "none";
                }
                enum 4 {
                    description "none";
                }
                enum 5 {
                    description "none";
                }
                enum 6 {
                    description "none";
                }
                enum 7 {
                    description "none";
                }
            }
            description "This enumeration lists one of PCP values or DISCARD.";
        }
        typedef percentage {
            type int64;
            description "Data type for percentage, 0%-100%.";
        }
        typedef physical-layer {
            type enumeration {
                enum 10base2 {
                    description "none";
                }
                enum 10base5 {
                    description "none";
                }
                enum 10base-f {
                    description "none";
                }
                enum 10base-fb {
                    description "none";
                }
                enum 10base-fl {
                    description "none";
                }
                enum 10base-fp {
                    description "none";
                }
                enum 10base-t {
                    description "none";
                }
                enum 10base-te {
                    description "none";
                }
                enum 10broad36 {
                    description "none";
                }
                enum 10pass-ts {
                    description "none";
                }
                enum 100base-bx10 {
                    description "none";
                }
                enum 100base-fx {
                    description "none";
                }
                enum 100base-lx10 {
                    description "none";
                }
                enum 100base-t {
                    description "none";
                }
                enum 100base-t2 {
                    description "none";
                }
                enum 100base-t4 {
                    description "none";
                }
                enum 100base-tx {
                    description "none";
                }
                enum 100base-x {
                    description "none";
                }
                enum 1000base-bx10 {
                    description "none";
                }
                enum 1000base-cx {
                    description "none";
                }
                enum 1000base-kx {
                    description "none";
                }
                enum 1000base-lx {
                    description "none";
                }
                enum 1000base-lx10 {
                    description "none";
                }
                enum 1000base-px10 {
                    description "none";
                }
                enum 1000base-px20 {
                    description "none";
                }
                enum 1000base-sx {
                    description "none";
                }
                enum 1000base-t {
                    description "none";
                }
                enum 1000base-x {
                    description "none";
                }
                enum 10gbase-cx4 {
                    description "none";
                }
                enum 10gbase-e {
                    description "none";
                }
                enum 10gbase-er {
                    description "none";
                }
                enum 10gbase-ew {
                    description "none";
                }
                enum 10gbase-kr {
                    description "none";
                }
                enum 10gbase-kx4 {
                    description "none";
                }
                enum 10gbase-l {
                    description "none";
                }
                enum 10gbase-lr {
                    description "none";
                }
                enum 10gbase-lrm {
                    description "none";
                }
                enum 10gbase-lw {
                    description "none";
                }
                enum 10gbase-lx4 {
                    description "none";
                }
                enum 10gbase-pr {
                    description "none";
                }
                enum 10gbase-prx {
                    description "none";
                }
                enum 10gbase-r {
                    description "none";
                }
                enum 10gbase-s {
                    description "none";
                }
                enum 10gbase-sr {
                    description "none";
                }
                enum 10gbase-sw {
                    description "none";
                }
                enum 10gbase-t {
                    description "none";
                }
                enum 10gbase-w {
                    description "none";
                }
                enum 10gbase-x {
                    description "none";
                }
                enum 100gbase-r {
                    description "none";
                }
                enum 100gbase-cr10 {
                    description "none";
                }
                enum 100gbase-er4 {
                    description "none";
                }
                enum 100gbase-lr4 {
                    description "none";
                }
                enum 100gbase-sr10 {
                    description "none";
                }
                enum 40gbase-r {
                    description "none";
                }
                enum 40gbase-cr4 {
                    description "none";
                }
                enum 40gbase--fr {
                    description "none";
                }
                enum 40gbase-kr4 {
                    description "none";
                }
                enum 40gbase-lr4 {
                    description "none";
                }
                enum 40gbase-sr4 {
                    description "none";
                }
                enum 1base5 {
                    description "none";
                }
                enum 2base-tl {
                    description "none";
                }
                enum 1g-epon {
                    description "none";
                }
                enum 10g-epon {
                    description "none";
                }
                enum 10-1g-epon {
                    description "none";
                }
                enum 10-10g-epon {
                    description "none";
                }
                enum other {
                    description "none";
                }
                enum none {
                    description "none";
                }
            }
            description "IEEE802.3 (2012) defined list excluding 1000BASE-PX-D and 1000BASE-PX-U. NONE is added with further MEF 10.3 discussion, for supporting logical interfaces.";
        }
        grouping physical-layer-per-link-g {
            leaf link-id {
                type natural-number;
                description "This is the link ID.";
            }
            leaf physical-layer {
                type physical-layer;
                description "This is the physical layer. IEEE802.3 (2012) defined.";
            }
            description "A link may consist of one or more physical ports. This data type includes the link ID and the physical port associated to the link Id.";
        }
        typedef pm-metric-type {
            type enumeration {
                enum fd {
                    description "Frame Delay Performance Metric.";
                }
                enum fdr {
                    description "Frame Delay Range Performance Metric.";
                }
                enum mfd {
                    description "Mean Frame Delay Performance Metric.";
                }
                enum ifdv {
                    description "Inter Frame Delay Variation Performance Metric.";
                }
                enum flr {
                    description "Frame Loss Ratio Performance Metric.";
                }
                enum av {
                    description "Availability Performance Metric.";
                }
                enum hli {
                    description "High Loss Interval Performance Metric.";
                }
                enum chli {
                    description "Consecutive High Loss Interval Performance Metric.";
                }
                enum group-av {
                    description "Group Availability (for a single EVC/OVC) Performance Metric.";
                }
                enum cpm {
                    description "Composite Performance Metric. Refer to MEF 10.3.1.";
                }
            }
            description "This enumeration provides the list of PM Metric types, including FD, MFD, FDR, IFDV, FLR, AV, HLI, CHLI, GROUP_AV, and CPM.";
        }
        typedef pm-unit {
            type enumeration {
                enum millisecond {
                    description "Measured Performance Metric in PM report as milliseconds, for FD, FDR, IFDV, and MFD.";
                }
                enum count {
                    description "Measured Performance Metric in PM report as count number, for HLI and CHLI.";
                }
                enum percent {
                    description "Measured Performance Metric in PM report as percentage, for FLR, Availability, Group Availability and Composite PM.";
                }
            }
            description "PM Unit, used for pairing with Value in data type PmUnitAndValue. Can be second, millisecond, micro second, etc. ";
        }
        grouping pm-unit-and-value-g {
            leaf pm-unit {
                type pm-unit;
                description "This attribute denotes the 'unit',  e.g., MILLISECOND, COUNT or PERCENT.";
            }
            leaf delay-value {
                type uint64;
                description "This attribute denotes the delay value only when the PmUnit=SECOND. It is for FD, FDR, MFD, IFDV.";
            }
            leaf count-value {
                type natural-number;
                description "This attribute denotes the count value only when the PmUnit=COUNT. It is for HLI and CHLI.";
            }
            leaf percent-value {
                type percentage;
                description "This attribute denotes the percentage value only when the PmUnit=PERCENT. It is for FLR, AV, GROUP_AV and CPM.";
            }
            description "This data type provides the pair of <unit, value> where the unit can be ms (for frame delay), number (for HLI), and value is the correspondent value for that unit.";
        }
        typedef positive-integer {
            type int64;
            description "An integer >0";
        }
        typedef service-state {
            type enumeration {
                enum pending {
                    description "none";
                }
                enum active {
                    description "none";
                }
                enum inactive {
                    description "none";
                }
            }
            description "This enumeration is for Service State.";
        }
        grouping source-mac-address-limit-g {
            leaf limit {
                type natural-number;
                description "This attribute denotes the maximum acceptable source MAC addresses.";
            }
            leaf time-interval {
                type natural-number;
                description "This attribute denotes the time interval in milliseconds.";
            }
            description "This limits the number of source MAC Addresses that can be used in ingress external interface frames mapped to the End Point of all types over a time interval.";
        }
        typedef svlan-id-control {
            type enumeration {
                enum full {
                    description "Operator can support only a single SP/SO (Service Provider/Super Operator) at the ENNI.";
                }
                enum partial {
                    description "Operator can support only multiple SP/SO (Service Provider/Super Operator) at the ENNI";
                }
            }
            description "This lists the S Vlan ID Control, either FULL or PARTIAL.";
        }
        grouping sync-mode-per-link-g {
            leaf link-id {
                type natural-number;
                description "This is the link ID of the link in the Aggregation Link.";
            }
            leaf sync-mode-enabled {
                type boolean;
                description "This attribute denotes whether the Synchronous Mode is enabled (on the link with the Link ID).";
            }
            description "A link may consist of one or more physical ports. This data type includes the link ID and the sync mode of the physical port associated to the link Id.";
        }
        typedef tagged-l2cp-processing {
            type enumeration {
                enum 802-1-compliant {
                    description "none";
                }
                enum 802-1-non-compliant {
                    description "none";
                }
            }
            description "Either 802.1 compliant or not. Refer to MEF 45.";
        }
        grouping time-and-date-g {
            leaf year {
                type positive-integer;
                description "This denotes the year.";
            }
            leaf month {
                type positive-integer;
                description "This denotes the month.";
            }
            leaf day {
                type positive-integer;
                description "This denotes the day.";
            }
            leaf hour {
                type natural-number;
                description "This denotes the hour.";
            }
            leaf minute {
                type natural-number;
                description "This denotes the minute.";
            }
            leaf second {
                type natural-number;
                description "This denotes the second.";
            }
            description "This data type is for Time and Date in UTC.";
        }
        grouping time-interval-t-g {
            leaf unit {
                type time-interval-unit;
                description "Month, week, day, hour, etc.";
            }
            leaf number {
                type positive-integer;
                description "This denotes the value (for the unit), e.g., 1 (month), 20 (day), etc.";
            }
            description "Time interval T for PM. E.g., 1 month, 20 days, 2 weeks, etc.";
        }
        typedef time-interval-unit {
            type enumeration {
                enum year {
                    description "none";
                }
                enum month {
                    description "none";
                }
                enum week {
                    description "none";
                }
                enum day {
                    description "none";
                }
                enum hour {
                    description "none";
                }
                enum minute {
                    description "none";
                }
                enum second {
                    description "none";
                }
            }
            description "Time interval unit, e.g., month, day, week, hour, etc.";
        }
        grouping vlan-id-g {
            leaf vlan-id {
                type positive-integer;
                description "This is the Vlan ID value.";
            }
            description "This is for VLAN ID from 1 to 4094";
        }
        grouping vlan-id-listing-g {
            leaf type {
                type vlan-id-mapping-type;
                description "Can be LIST, or ALL, or EXCEPT.";
            }
            list vlan-id-list {
                key 'vlan-id';
                uses vlan-id-g;
                description "This is a list of Vlan IDs.";
            }
            description "The list VLAN IDs, either when type=LIST, or when type==EXCEPT (which means the VLAN IDs except the listed). When type=ALL, the vlanId list is not applicable.";
        }
        typedef vlan-id-mapping-type {
            type enumeration {
                enum all {
                    description "All Vlan IDs.";
                }
                enum except {
                    description "All Vlan IDs except the listed.";
                }
                enum list {
                    description "List of Vlan IDs.";
                }
            }
            description "Vlan ID types, ALL for all vlan IDs, LIST for a list of Vlan IDs, EXCEPT for all Vlan IDs except the listed. ";
        }
        typedef vlan-id-preservation {
            type enumeration {
                enum preserve {
                    description "To achieve EVC CE-VLAN ID Preservation.";
                }
                enum retain {
                    description "C-Tag, if present, is encapsulated with the C-Tag VLAN ID value retained.";
                }
                enum strip {
                    description "C-Tag is discarded.";
                }
            }
            description "This is for Vlan ID Preservation. Refer to MEF 26.2 section 12.7.";
        }
        typedef vlan-tag {
            type enumeration {
                enum s-tag {
                    description "none";
                }
                enum c-tag {
                    description "none";
                }
            }
            description "This is for Vlan Tag type, i.e., S-tag or C-tag.";
        }
        grouping vlan-id-list-or-untag-g {
            leaf type {
                type vlan-id-mapping-type-or-untag;
                description "none";
            }
            list vlan-id-list {
                key 'vlan-id';
                uses vlan-id-g;
                description "none";
            }
            description "none";
        }
        typedef vlan-id-mapping-type-or-untag {
            type enumeration {
                enum all {
                    description "none";
                }
                enum except {
                    description "none";
                }
                enum list {
                    description "none";
                }
                enum untagged {
                    description "none";
                }
            }
            description "Vlan ID types, ALL for all Vlan IDs, LIST for a list of Vlan IDs, EXCEPT for all Vlan IDs except the listed, UNTAGGED to indicate that untagged and priority-tagged frames are mapped to this end point.";
        }

}
