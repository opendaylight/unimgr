/*
 * Copyright (c) 2018 Amartus and others. All rights reserved.
 *
 * This program and the accompanying materials are made available under the
 * terms of the Eclipse Public License v1.0 which accompanies this distribution,
 * and is available at http://www.eclipse.org/legal/epl-v10.html
 */


module topology-ext {

    yang-version 1;
    namespace "urn:odl:unimgr:yang:topology-ext";

    prefix "topology-ext";

    import ietf-inet-types { prefix "inet"; revision-date 2013-07-15; }
    import network-topology { prefix "topo"; revision-date 2013-10-21; }
    import yang-ext { prefix "ext"; }

    revision "2018-05-31" {
        description "Loopback extension";
    }

    augment "/topo:network-topology/topo:topology/topo:node" {
        description "Augmentation for loopback address nodes under topology";
        ext:augment-identifier "loopback-augmentation";
        leaf loopback-address {
         type inet:ip-address;
        }
    }

}
